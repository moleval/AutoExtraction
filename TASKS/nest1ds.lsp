;;; ============================================================
;;; NEST1DS.LSP — раскрой хлыстов по выбранным элементам
;;; Команда: NEST1DS
;;; Поддержка: LWPOLYLINE, POLYLINE, LINE, ARC, ELLIPSE, SPLINE, MLINE
;;; Алгоритм: First-Fit Decreasing (FFD)
;;; ============================================================
(vl-load-com)

;; ---------- развернуть (длина, кол-во) в список длин, по убыванию ----------
;; ВАЖНО: не сортируем итоговый список с дубликатами.
;; Сначала сортируем ГРУППЫ по длине, затем разворачиваем каждую группу.
(defun n1-expand (pieces / sorted-groups out rec len cnt i)
  ;; 1. Сортируем группы по убыванию длины
  (setq sorted-groups
    (vl-sort
      pieces
      '(lambda (a b)
         (> (car a) (car b))
       )
    )
  )

  ;; 2. Разворачиваем каждую группу в нужное количество отрезков
  (setq out '())

  (foreach rec sorted-groups
    (setq len (car rec))
    (setq cnt (fix (cadr rec)))

    (princ
      (strcat
        "\n[n1-expand] группа: "
        (rtos len 2 0)
        " x "
        (itoa cnt)
      )
    )

    (setq i 0)
    (while (< i cnt)
      (setq out (append out (list len)))
      (setq i (1+ i))
    )
  )

  (princ
    (strcat
      "\n[n1-expand] ИТОГО развёрнуто: "
      (itoa (length out))
    )
  )

  out
)

;; ---------- замена n-го элемента списка ----------
(defun n1-replace-nth (lst idx new / i out)
  (setq i 0 out '())
  (foreach x lst
    (if (= i idx)
      (setq out (append out (list new)))
      (setq out (append out (list x)))
    )
    (setq i (1+ i))
  )
  out
)

;; ---------- FFD: список хлыстов (остаток отр1 отр2 ...) ----------
(defun n1-ffd (sorted-pieces stock kerf / bars p placed j bar newbar)
  (setq bars '())
  (foreach p sorted-pieces
    (setq placed nil)
    (setq j 0)
    (while (and (not placed) (< j (length bars)))
      (setq bar (nth j bars))
      (if (>= (car bar) (+ p kerf))
        (progn
          (setq newbar (cons (- (car bar) (+ p kerf))
                             (append (cdr bar) (list p))))
          (setq bars (n1-replace-nth bars j newbar))
          (setq placed T)
        )
      )
      (setq j (1+ j))
    )
    (if (not placed)
      (setq bars (append bars (list (list (- stock (+ p kerf)) p))))
    )
  )
  bars
)

;; ---------- длина мультилинии (MLINE) ----------
(defun n1-mline-length (ent / obj numEl copyObj arr safe sub elen total)
  (setq numEl (cdr (assoc 72 (entget ent))))
  (if (or (null numEl) (< numEl 1)) (setq numEl 1))
  (setq obj (vlax-ename->vla-object ent))
  (setq copyObj (vla-Copy obj))
  (setq arr (vl-catch-all-apply 'vla-Explode (list copyObj)))
  (if (vl-catch-all-error-p arr)
    (progn
      (vl-catch-all-apply 'vla-Delete (list copyObj))
      nil
    )
    (progn
      (setq safe (vlax-safearray->list (vlax-variant-value arr)))
      (setq total 0.0)
      (foreach sub safe
        (setq elen
          (vl-catch-all-apply
            'vlax-curve-getDistAtParam
            (list (vlax-vla-object->ename sub)
                  (vlax-curve-getEndParam (vlax-vla-object->ename sub)))))
        (if (numberp elen) (setq total (+ total elen)))
        (vl-catch-all-apply 'vla-Delete (list sub))
      )
      (/ total (float numEl))
    )
  )
)

;; ---------- добавить ключ в группы ----------
(defun n1-add-group (groups key / found)
  (setq found (assoc key groups))
  (if found
    (mapcar '(lambda (x) (if (= (car x) key) (cons (car x) (1+ (cdr x))) x)) groups)
    (cons (cons key 1) groups)
  )
)

;; ---------- извлечение длин с группировкой и диагностикой ----------
(defun n1-extract-pieces (ss tol / i ent typ len key pieces total measured skipped)
  (setq pieces '())
  (setq i 0)
  (setq total (sslength ss))
  (setq measured 0)
  (setq skipped 0)
  (repeat total
    (setq ent (ssname ss i))
    (setq typ (cdr (assoc 0 (entget ent))))
    (if (= typ "MLINE")
      (setq len (n1-mline-length ent))
      (setq len (vl-catch-all-apply 'vlax-curve-getDistAtParam
                  (list ent (vlax-curve-getEndParam ent))))
    )
    (if (and (numberp len) (> len 0.0))
      (progn
        (setq measured (1+ measured))
        (setq key (fix (+ (/ len tol) 0.5)))
        (setq pieces (n1-add-group pieces key))
      )
      (setq skipped (1+ skipped))
    )
    (setq i (1+ i))
  )
  (princ (strcat "\nИзмерено: " (itoa measured) " из " (itoa total)
                 (if (> skipped 0) (strcat ", пропущено: " (itoa skipped)) "")))
  (mapcar '(lambda (x) (list (* (float (car x)) tol) (cdr x))) (reverse pieces))
)

;; ---------- список длин в строку ----------
(defun n1-list-to-str (lst / s x)
  (setq s "")
  (foreach x lst (setq s (strcat s (if (= s "") "" " ") (rtos x 2 0))))
  s
)

;; ---------- графические примитивы ----------
(defun n1-draw-line (p1 p2)
  (entmake (list '(0 . "LINE")
                 (cons 10 (list (car p1) (cadr p1) 0.0))
                 (cons 11 (list (car p2) (cadr p2) 0.0))))
)

(defun n1-draw-rect (p1 p2 / x1 y1 x2 y2)
  (setq x1 (car p1) y1 (cadr p1) x2 (car p2) y2 (cadr p2))
  (entmake (list '(0 . "LWPOLYLINE") '(100 . "AcDbEntity") '(100 . "AcDbPolyline")
                 (cons 90 4) (cons 70 1)
                 (cons 10 (list x1 y1)) (cons 10 (list x2 y1))
                 (cons 10 (list x2 y2)) (cons 10 (list x1 y2))))
)

(defun n1-draw-text (pt h str)
  (entmake (list '(0 . "TEXT") (cons 10 (list (car pt) (cadr pt) 0.0))
                 (cons 40 h) (cons 1 str) (cons 50 0.0)))
)

;; ---------- визуализация раскроя ----------
(defun n1-draw-layout (bars stock kerf insPt / barHeight gap txtH x0 y0 maxy miny i bar pieces waste used util curx p halfw str)
  (setq barHeight (/ stock 30.0))
  (setq gap (* barHeight 0.7))
  (setq txtH (* barHeight 0.30))
  (setq x0 (car insPt))
  (setq y0 (cadr insPt))
  (setq maxy (+ y0 barHeight))
  (setq miny y0)
  (setq i 0)
  (foreach bar bars
    (setq i (1+ i))
    (setq pieces (cdr bar))
    (setq waste (car bar))
    (setq used (- stock waste))
    (setq util (* 100.0 (/ used stock)))
    (setq miny y0)
    (n1-draw-rect (list x0 y0) (list (+ x0 stock) (+ y0 barHeight)))
    (n1-draw-text (list (- x0 (* barHeight 2.2)) (+ y0 (* barHeight 0.35))) txtH
                  (strcat "Хлыст " (itoa i) "  [" (rtos util 2 1) "%]"))
    (setq curx x0)
    (foreach p pieces
      (n1-draw-line (list curx y0) (list curx (+ y0 barHeight)))
      (setq str (rtos p 2 0))
      (setq halfw (* (strlen str) txtH 0.4))
      (n1-draw-text (list (+ curx (* p 0.5) (- halfw)) (+ y0 (* barHeight 0.35))) txtH str)
      (setq curx (+ curx p kerf))
    )
    (n1-draw-line (list curx y0) (list curx (+ y0 barHeight)))
    (if (> waste 0.0)
      (progn
        (setq str (strcat "отход " (rtos waste 2 0)))
        (setq halfw (* (strlen str) txtH 0.4))
        (n1-draw-text (list (+ curx (* waste 0.5) (- halfw)) (+ y0 (* barHeight 0.35))) txtH str)
      )
    )
    (setq y0 (- y0 barHeight gap))
  )
  (princ (strcat "\nВизуализация создана: хлыстов " (itoa (length bars)) "."))
  (list (list x0 miny) (list (+ x0 stock) maxy))
)

;; ---------- отчёт в командную строку ----------
(defun n1-report (bars stock kerf / i bar pieces waste used util)
  (princ (strcat "\nВсего хлыстов: " (itoa (length bars))))
  (setq i 0)
  (foreach bar bars
    (setq i (1+ i))
    (setq pieces (cdr bar))
    (setq waste (car bar))
    (setq used (- stock waste))
    (setq util (* 100.0 (/ used stock)))
    (princ (strcat "\nХлыст " (itoa i) ": " (n1-list-to-str pieces)
                   " | исп. " (rtos used 2 1) " | отход " (rtos waste 2 1) " | " (rtos util 2 1) "%"))
  )
  (princ)
)

;; ---------- экспорт в CSV ----------
(defun n1-write-csv (bars stock kerf / fname f i bar pieces waste used util)
  (setq fname (strcat (getvar "DWGPREFIX") "nest1ds_result.csv"))
  (setq f (open fname "w"))
  (if f
    (progn
      (write-line "Хлыст;Отрезки;Использовано;Отход;Использование_%" f)
      (setq i 0)
      (foreach bar bars
        (setq i (1+ i))
        (setq pieces (cdr bar))
        (setq waste (car bar))
        (setq used (- stock waste))
        (setq util (* 100.0 (/ used stock)))
        (write-line (strcat (itoa i) ";" (n1-list-to-str pieces) ";" (rtos used 2 1) ";"
                            (rtos waste 2 1) ";" (rtos util 2 1)) f)
      )
      (close f)
      (princ (strcat "\nCSV сохранён: " fname))
    )
  )
)

;; ---------- главная команда ----------
(defun c:NEST1DS ( / ss tol stock kerf insPt pieces sorted bars bbox dbg-cnt p1 p2)
  (princ "\n=== РАСКРОЙ ХЛЫСТОВ ПО ВЫБРАННЫМ ЭЛЕМЕНТАМ ===")
  (princ "\nВыберите полилинии/линии - будущие отрезки:")
  (setq ss (ssget '((0 . "LWPOLYLINE,POLYLINE,LINE,ARC,ELLIPSE,SPLINE,MLINE"))))
  (if (null ss) (progn (princ "\nНичего не выбрано.") (princ) (exit)))
  (princ (strcat "\nВыбрано объектов: " (itoa (sslength ss))))
  (setq tol (getreal "\nТочность группировки длин (мм) <1>: "))
  (if (or (null tol) (<= tol 0.0)) (setq tol 1.0))
  (setq stock (getreal "\nДлина хлыста (мм) <6000>: "))
  (if (null stock) (setq stock 6000.0))
  (setq kerf (getreal "\nШирина реза (мм) <0>: "))
  (if (null kerf) (setq kerf 0.0))
  (setq pieces (n1-extract-pieces ss tol))
  (if (null pieces) (progn (princ "\nНе удалось получить длины.") (princ) (exit)))
  (setq dbg-cnt 0)
  (foreach rec pieces (setq dbg-cnt (+ dbg-cnt (cadr rec))))
  (princ (strcat "\n[ДИАГ] Групп длин: " (itoa (length pieces)) ", всего отрезков: " (itoa dbg-cnt)))
  (foreach rec pieces
    (if (> (car rec) stock)
      (princ (strcat "\nВНИМАНИЕ: отрезок " (rtos (car rec) 2 2) " длиннее хлыста!"))
    )
  )
  (setq sorted (n1-expand pieces))
  (princ (strcat "\n[ДИАГ] Развёрнуто отрезков: " (itoa (length sorted))))
  (setq bars (n1-ffd sorted stock kerf))
  (princ (strcat "\n[ДИАГ] Хлыстов после раскроя: " (itoa (length bars))))
  (n1-report bars stock kerf)
  (setq insPt (getpoint "\nУкажите точку вставки визуализации: "))
  (if insPt
    (progn
      (setq bbox (n1-draw-layout bars stock kerf insPt))
      (if bbox
        (progn
          (setq p1 (vlax-3d-point (list (car (car bbox)) (cadr (car bbox)) 0.0)))
          (setq p2 (vlax-3d-point (list (car (cadr bbox)) (cadr (cadr bbox)) 0.0)))
          (vl-catch-all-apply 'vla-ZoomWindow (list (vlax-get-acad-object) p1 p2))
        )
      )
    )
    (princ "\nВизуализация пропущена.")
  )
  (n1-write-csv bars stock kerf)
  (princ)
)

(princ "\nNEST1DS.LSP загружен. Команда: NEST1DS")
(princ)
