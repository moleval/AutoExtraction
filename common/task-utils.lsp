;;; ============================================================
;;; common/task-utils.lsp
;;; Универсальные функции для задач AutoExtraction
;;
;;; ИСПРАВЛЕНИЯ (аудит Этап 4.3):
;;;   D3: Удалена функция tu-parse-comma-list.
;;;       Единственной функцией разбора строк является
;;;       универсальная функция split-string.
;;;       Поиск по проекту показал, что tu-parse-comma-list
;;;       нигде не вызывается, удаление безопасно.
;;
;;;   D9: Унификация суффиксов имен файлов.
;;;       Добавлены суффиксы для всех задач:
;;;       Фасонка, Подсистема, Заполнение, Облицовка, Витраж.
;;
;;; ПРОШЛЫЕ ИСПРАВЛЕНИЯ:
;;;   Этап 4.1 (D7): добавлена переменная pos в /-список
;;;       tu-strip-extension
;;;   Этап 4.2 (D4): оптимизация циклов — append заменен
;;;       на cons/reverse в функциях:
;;;       - tu-list-unique-ci
;;;       - split-string
;;;   Этап 4.2 (D14): исправление утечки файлового дескриптора
;;;       в функции tu-file-writable-p
;;; ============================================================

(vl-load-com)

;; ============================================================
;; Уникализация списка строк без учета регистра
;; ИСПРАВЛЕНО (аудит Этап 4.2, пункт D4):
;; Оптимизировано: cons вместо append (O(1) вместо O(N))
;; Порядок элементов сохраняется через reverse в конце.
;; ============================================================
(defun tu-list-unique-ci (lst / out x key)
  (setq out '())
  (if (listp lst)
    (foreach x lst
      (if (= (type x) 'STR)
        (progn
          (setq key (strcase x))
          (if (not (vl-some '(lambda (y) (= (strcase y) key)) out))
            (setq out (cons x out))
          )
        )
      )
    )
  )
  (reverse out)
)

;; Сортировка строк без учета регистра
(defun tu-sort-strings-ci (lst)
  (vl-sort lst '(lambda (a b) (< (strcase a) (strcase b))))
)

;; Удаление расширения из пути
;; Исправлено на Этапе 4.1: добавлена pos в /-список
(defun tu-strip-extension (path / pos)
  (if (setq pos (vl-string-position 46 (vl-string-left-trim "\\/" path) 0 T nil))
    (substr path 1 pos)
    path
  )
)

;; ============================================================
;; Формирование базового имени файла по умолчанию
;; ИСПРАВЛЕНО (аудит Этап 4.3, пункт D9):
;; Добавлены суффиксы для всех задач:
;; Фасонка, Подсистема, Заполнение, Облицовка, Витраж.
;; Ранее суффикс был только для Фасонки.
;; ============================================================
(defun tu-default-save-base (task-id)
  (strcat
    (getvar "dwgprefix")
    (vl-filename-base (getvar "dwgname"))
    (cond
      ((eq task-id 'FASONKA)    " Фасонка")
      ((eq task-id 'SUBSYSTEM)  " Подсистема")
      ((eq task-id 'ZAPOLNENIE) " Заполнение")
      ((eq task-id 'CLADDING)   " Облицовка")
      ((eq task-id 'VITRAZH)    " Витраж")
      (t "")
    )
  )
)

;; Запрос базового имени для сохранения
(defun tu-get-save-base (task-id / default)
  (setq default (tu-default-save-base task-id))
  (getfiled "Сохранить как" default "xls" 1)
)

;; ============================================================
;; Проверка возможности записи файла
;; ИСПРАВЛЕНО (аудит Этап 4.2, пункт D14):
;; Файловый дескриптор теперь закрывается после проверки.
;; ============================================================
(defun tu-file-writable-p (path / f)
  (setq f (open path "a"))
  (if f
    (progn
      (close f)
      T
    )
    nil
  )
)

;; ============================================================
;; РАЗБОР СТРОК
;; ИСПРАВЛЕНО (аудит Этап 4.3, пункт D3):
;; Функция tu-parse-comma-list удалена.
;; Единственной функцией разбора строк является
;; универсальная функция split-string.
;; Поиск по проекту показал, что tu-parse-comma-list
;; нигде не вызывается, удаление безопасно.
;; ============================================================

;; ============================================================
;; Разбиение строки на список по произвольному разделителю
;; Используется для разбора строки слоев, введенной через запятую
;; С обрезкой пробелов по краям каждого элемента.
;; Это гарантирует корректную работу при вводе слоев
;; вида "Заполнение, Стекло" (с пробелом после запятой).
;; Пример: (split-string "a, b ,c" ",") ? ("a" "b" "c")
;; ИСПРАВЛЕНО (аудит Этап 4.2, пункт D4):
;; Оптимизировано: cons вместо append (O(1) вместо O(N))
;; Порядок элементов сохраняется через reverse в конце.
;; ============================================================
(defun split-string (str delim / pos result item)
  (setq result '())
  (while (setq pos (vl-string-search delim str))
    (setq item (vl-string-trim " " (substr str 1 pos)))
    (setq result (cons item result))
    (setq str (substr str (+ pos 2)))
  )
  (setq item (vl-string-trim " " str))
  (if (> (strlen item) 0)
    (setq result (cons item result))
  )
  (reverse result)
)

;; TASK-UTILS.LSP загружен.
(princ)

;; ============================================================
;; Этап 2 (V11): единый диагностический протокол.
;; Тумблер *EXTRACTION-DIAGNOSTIC*: nil (по умолчанию) - тишина;
;; T - этапные строки [SCAN]/[FILTER]/[VALIDATION]/[PACK]/[DRAW]/[BLOCK].
;; Включается из командной строки AutoCAD: (setq *EXTRACTION-DIAGNOSTIC* T).
;; ============================================================
(setq *EXTRACTION-DIAGNOSTIC* nil)

(defun tu-diag (tag text)
  (if *EXTRACTION-DIAGNOSTIC*
    (princ (strcat "\n[" tag "] " text))))

;; ============================================================
;; Этап 3 (V8): единый guard системных переменных.
;; Паттерн SAVE -> MODIFY -> WORK -> RESTORE только для реально
;; изменяемых переменных. Любой обрыв (ESC/ошибка) обязан вернуть
;; исходные значения - возврат выполняет локальный *error* модуля.
;; ============================================================

;; Сохранить значения списка системных переменных.
;; Возвращает assoc-список (("NAME" . старое-значение) ...).
(defun tu-sysvar-save (names)
  (mapcar (function (lambda (n) (cons n (getvar n)))) names))

;; Вернуть значения, сохранённые tu-sysvar-save.
;; Сбой отдельного setvar не мешает восстановлению остальных.
(defun tu-sysvar-restore (saved)
  (foreach p saved
    (vl-catch-all-apply 'setvar (list (car p) (cdr p))))
  nil)

;; ============================================================
;; Этап 3 (V10): единый Undo-guard.
;; Вложенные пары схлопываются по счётчику *tu-undo-depth*: реальные
;; StartUndoMark/EndUndoMark ставятся только на внешнем уровне,
;; поэтому одна задача (с любыми внутренними парами) = одна Undo-
;; запись = один U.
;; tu-undo-begin  — открыть уровень (возвращает doc или nil).
;; tu-undo-end    — закрыть уровень; на нулевой глубине ставит
;;   реальный EndUndoMark.
;; tu-undo-cancel — закрыть ВСЕ уровни и откатить командой UNDO.
;;   ВНИМАНИЕ: метода vla-Undo в ActiveX Document НЕТ; cancel
;;   запускает команду UNDO, поэтому НЕ вызывать из *error* —
;;   только из обычного кода (см. V13). В обработчиках — tu-undo-end.
;; ============================================================
(if (null (boundp '*tu-undo-depth*)) (setq *tu-undo-depth* 0))
;; Счётчик модификаций БД на момент открытия внешней группы (предохранитель
;; tu-undo-cancel: ESC на промпте = группа пуста, UNDO НЕ выполнять).
(if (null (boundp '*tu-undo-dbmod*)) (setq *tu-undo-dbmod* 0))

(defun tu-undo-begin ( / doc)
  (setq doc (vl-catch-all-apply
              'vla-get-ActiveDocument (list (vlax-get-acad-object))))
  (if (and doc (not (vl-catch-all-error-p doc)))
    (progn
      (if (= *tu-undo-depth* 0)
        (progn
          (setq *tu-undo-dbmod* (getvar "DBMOD"))
          (vl-catch-all-apply 'vla-StartUndoMark (list doc))))
      (setq *tu-undo-depth* (1+ *tu-undo-depth*))
      doc)))

(defun tu-undo-end (doc)
  (if (and doc (not (vl-catch-all-error-p doc)) (> *tu-undo-depth* 0))
    (progn
      (setq *tu-undo-depth* (1- *tu-undo-depth*))
      (if (= *tu-undo-depth* 0)
        (vl-catch-all-apply 'vla-EndUndoMark (list doc)))))
  nil)

(defun tu-undo-cancel (doc / dbmod-now old-echo)
  ;; Откат ТОЛЬКО если в группе реально были изменения БД (DBMOD сдвинулся),
  ;; иначе UNDO _1 зацепил бы постороннюю правку пользователя.
  ;; Диагностика (ESC-тест П3): страж обещал "откачено автоматически", а по
  ;; факту откат не подтверждался - теперь решение печатается честно.
  (if (and doc (not (vl-catch-all-error-p doc)))
    (progn
      (setq *tu-undo-depth* 0)
      (vl-catch-all-apply 'vla-EndUndoMark (list doc))
      (setq dbmod-now (getvar "DBMOD"))
      (if (/= dbmod-now *tu-undo-dbmod*)
        (progn
          (setq old-echo (getvar "CMDECHO"))
          (setvar "CMDECHO" 1)
          (princ (strcat "\n[UNDO-CANCEL] изменения БД есть (DBMOD "
                         (itoa *tu-undo-dbmod*) " -> " (itoa dbmod-now)
                         "), выполняю UNDO 1..."))
          (vl-catch-all-apply 'vl-cmdf (list "_.UNDO" "_1"))
          (setvar "CMDECHO" old-echo)
          (princ (strcat "\n[UNDO-CANCEL] UNDO 1 завершён (DBMOD теперь "
                         (itoa (getvar "DBMOD")) ").")))
        (princ "\n[UNDO-CANCEL] изменений БД в группе нет - откат не требуется."))))
  nil)

;; ============================================================
;; Этап 3 (V9): единый контракт вызова ActiveX/AutoCAD API.
;; ex-safe-call: (fn (list args...)) -> (OK значение) | (ERROR "текст").
;; Оборачиваем ТОЛЬКО внешние вызовы AutoCAD/ActiveX (не кадую строку).
;; Точки миграции: docs/v9-activex-migration.md
;; ============================================================
(defun ex-safe-call (fn args / r)
  ;; fn - символ ActiveX/API-функции, args - список аргументов (как в
  ;; vl-catch-all-apply). Возвращает (OK значение) | (ERROR "текст").
  ;; Точечная нотация dot-rest НЕ используется (читатель AutoCAD на ней
  ;; выдавал ошибку загрузки).
  (setq r (vl-catch-all-apply fn args))
  (if (vl-catch-all-error-p r)
    (list 'ERROR (vl-catch-all-error-message r))
    (list 'OK r)))

(defun ex-safe-ok-p (cell)     (eq (car cell) 'OK))
(defun ex-safe-value (cell)    (cadr cell))
(defun ex-safe-message (cell)  (cadr cell))

;; ------------------------------------------------------------
;; U3: общий генератор уникальных имён для рапорт-блоков
;; («Раскрой Эксперимент 0», «Раскрой Эксперимент 1», ...).
;; Кандидат считается свободным, если его нет в таблице BLOCK.
;; ------------------------------------------------------------
(defun tu-unique-block-name (base / n name)
  (setq n 0 name (strcat base " " (itoa n)))
  (while (tblsearch "BLOCK" name)
    (setq n (1+ n) name (strcat base " " (itoa n))))
  name)


;; ------------------------------------------------------------
;; DCL: динамический заголовок рамки
;; Заголовок кластера (boxed_column) в DCL статичен: у кластера нет
;; ключа, set_tile на него не действует. Чтобы показать в заголовке
;; счётчик, файл диалога копируется во временный с заменой строки
;; label. Любая неудача — возвращается ИСХОДНЫЙ файл: окно откроется
;; как раньше, просто с обычным заголовком.
;; ------------------------------------------------------------

;; В заголовке DCL недопустимы кавычка и обратный слэш
(defun tu-dcl-safe-label (s / out i ch)
  (setq out "" i 1)
  (if (= (type s) 'STR)
    (repeat (strlen s)
      (setq ch (substr s i 1))
      (if (and (/= ch "\"") (/= ch "\\"))
        (setq out (strcat out ch))
      )
      (setq i (1+ i))
    )
  )
  out
)

;; Копия .dcl, в которой первая строка с подстрокой anchor заменена
;; заголовком new-label. Возвращает путь к копии либо исходный путь.
(defun tu-dcl-with-label (src anchor new-label / tmp fin fout line done res)
  (setq new-label (tu-dcl-safe-label new-label))
  (setq done nil tmp nil)
  (if (and (= (type src) 'STR)
           (= (type anchor) 'STR)
           (/= new-label "")
           (findfile src))
    (progn
      (setq tmp (vl-filename-mktemp "ae_dcl" nil ".dcl"))
      (setq fin (open src "r"))
      (setq fout (if fin (open tmp "w")))
      (if (and fin fout)
        (progn
          (while (setq line (read-line fin))
            (if (and (not done) (vl-string-search anchor line))
              (progn
                (write-line (strcat "    label = \"" new-label "\";") fout)
                (setq done T)
              )
              (write-line line fout)
            )
          )
          (close fin)
          (close fout)
        )
        (progn
          (if fin (close fin))
          (if fout (close fout))
        )
      )
    )
  )
  (setq res (if done tmp src))
  (if (and tmp (not done)) (vl-catch-all-apply 'vl-file-delete (list tmp)))
  res
)

;; Удалить временную копию (исходный файл не трогает)
(defun tu-dcl-cleanup (path src)
  (if (and (= (type path) 'STR) (= (type src) 'STR) (/= path src))
    (vl-catch-all-apply 'vl-file-delete (list path))
  )
  nil
)

;; Склонение слова «слой»: 1 слой, 2 слоя, 5 слоев, 11 слоев
(defun tu-layer-word (n / n10 n100)
  (if (not (numberp n)) (setq n 0))
  (setq n (fix (abs n)))
  (setq n100 (rem n 100) n10 (rem n 10))
  (cond
    ((and (>= n100 11) (<= n100 14)) "слоев")
    ((= n10 1) "слой")
    ((and (>= n10 2) (<= n10 4)) "слоя")
    (T "слоев")
  )
)


;; ------------------------------------------------------------
;; МАРКА ЭЛЕМЕНТА (атрибут вставки блока)
;; Тег сравнивается без учёта регистра и пробелов по краям.
;; Любая ошибка ActiveX гасится: отсутствие марки — это nil, а не сбой
;; задачи. Карта раскроя не должна падать из-за подписи.
;; ------------------------------------------------------------

;; Имя атрибута с маркой. Меняется здесь, если в чертежах другой тег.
(if (not (boundp '*AE-MARK-ATTR*))
  (setq *AE-MARK-ATTR* "МАРКА")
)

;; Значение атрибута блока по тегу либо nil
(defun tu-block-attr (obj tag / attrs a tagname value result)
  (setq result nil)
  (setq attrs (vl-catch-all-apply 'vlax-invoke (list obj 'GetAttributes)))
  (if (or (vl-catch-all-error-p attrs) (not (listp attrs)))
    nil
    (progn
      (foreach a attrs
        (if (null result)
          (progn
            (setq tagname (vl-catch-all-apply 'vla-get-TagString (list a)))
            (if (and (not (vl-catch-all-error-p tagname))
                     (= (type tagname) 'STR)
                     (= (strcase (vl-string-trim " \t" tagname)) (strcase tag)))
              (progn
                (setq value (vl-catch-all-apply 'vla-get-TextString (list a)))
                (if (and (not (vl-catch-all-error-p value))
                         (= (type value) 'STR))
                  (setq value (vl-string-trim " \t" value))
                  (setq value nil))
                (if (and value (/= value "")) (setq result value)))))))
      result))
)

;; Краткая строка марок для колонки таблицы. Длинный список не
;; растягивает колонку: вместо перечисления даётся «первая +N».
(defun tu-marks-brief (marks maxlen / out s n tail)
  (setq out '())
  (if (listp marks)
    (foreach m marks
      (if (and (= (type m) 'STR) (/= m "") (not (member m out)))
        (setq out (append out (list m))))))
  (if (null out)
    ""
    (progn
      (setq s "")
      (foreach m out (setq s (if (= s "") m (strcat s ", " m))))
      (if (<= (strlen s) maxlen)
        s
        (progn
          (setq n (1- (length out)))
          (if (> n 0)
            ;; ВАЖНО: хвост « +N» входит в предел. Без обрезки первой
            ;; марки свёртка выходила ДЛИННЕЕ колонки и наезжала на
            ;; соседнюю — «ТБ-1 Рг5.1бдв +1» рядом с «2» читалось «+12».
            (progn
              (setq tail (strcat " +" (itoa n)))
              (strcat (substr (car out) 1 (max 1 (- maxlen (strlen tail))))
                      tail))
            (substr (car out) 1 maxlen))))))
)

;; Сколько символов влезает в колонку шириной colW при высоте текста
;; textH. Ширина знака в шрифтах карты около 0.6 высоты; один знак
;; оставляем на зазор до соседней колонки.
(defun tu-fit-chars (colW textH / n)
  (if (or (not (numberp colW)) (not (numberp textH)) (<= textH 0.0))
    8
    (progn
      (setq n (1- (fix (/ colW (* textH 0.6)))))
      (if (< n 3) 3 n)))
)

;; Марка объекта: только у вставок блоков, у прочих типов nil
(defun tu-entity-mark (ent / ed obj v)
  (setq v nil)
  (if (and ent (= (type ent) 'ENAME))
    (progn
      (setq ed (vl-catch-all-apply 'entget (list ent)))
      (if (and (not (vl-catch-all-error-p ed))
               (= (cdr (assoc 0 ed)) "INSERT"))
        (progn
          (setq obj (vl-catch-all-apply 'vlax-ename->vla-object (list ent)))
          (if (not (vl-catch-all-error-p obj))
            (setq v (tu-block-attr obj *AE-MARK-ATTR*)))))))
  v
)
