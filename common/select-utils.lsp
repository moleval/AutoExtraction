;;; ============================================================
;;; common/select-utils.lsp
;;; Выбор вхождений блоков и извлечение динамических свойств
;;
;;; РЕДАКЦИЯ 4: каноническое имя su-layer-selected-p во всех
;;; внутренних вызовах + алиас su_layer_selected-p для
;;; совместимости со старыми вызовами других модулей.
;;
;;; Состав:
;;;   su-layer-selected-p     — принадлежность слоя списку
;;;   su-value-to-number      — значение в число
;;;   кэш свойств блоков      — su-get-block-props (Р3.3)
;;;   su-select-inserts       — выбор INSERT (Р2.2)
;;;   su-get-effective-name / su-get-visibility
;;;   su-is-valid-stock-block
;;;   su-get-dynblock-type-name / su-collect-dynblock-types (3.1)
;;;   su-get-length           — двухступенчатый поиск (Р3.2)
;;;   MLINE: su-mline-vertices,
;;;          su-mline-vertex-count, su-mline-style-name,
;;;          su-mline-type-name, su-collect-mline-types,
;;;          su-count-mline-by-type, su-mline-cut-geom (M2.1, DXF)
;;;   su-layer-match-any, *su-cutline-types*
;;;   su-filter-ss-cutline, su-filter-dynblocks,
;;;   su-build-cutline-ssfilter, su-select-cutline-objects
;;;   su-select-lwpolylines   — выбор LWPOLYLINE (Облицовка К1)
;;; ============================================================
(vl-load-com)

;; ============================================================
;; Проверка, принадлежит ли слой выбранному списку
;; ============================================================
(defun su-layer-selected-p (layer layers / x)
  (if (null layers)
    T
    (progn
      (setq x nil)
      (foreach name layers
        (if (= (strcase name) (strcase layer))
          (setq x T)
        )
      )
      x
    )
  )
)

;; ============================================================
;; Преобразование значения в число
;; ============================================================
(defun su-value-to-number (value / x s)
  (cond
    ((numberp value)
     (float value)
    )
    ((= (type value) 'VARIANT)
     (setq x (vl-catch-all-apply 'vlax-variant-value (list value)))
     (if (vl-catch-all-error-p x)
       nil
       (su-value-to-number x)
     )
    )
    ((= (type value) 'STR)
     (setq s (vl-string-trim " \t\r\n" value))
     (if (> (strlen s) 0)
       (progn
         (setq s (vl-string-translate "," "." s))
         (while (vl-string-search " " s)
           (setq s (vl-string-subst "" " " s))
         )
         (setq x (vl-catch-all-apply 'atof (list s)))
         (if (vl-catch-all-error-p x)
           nil
           x
         )
       )
       nil
     )
    )
    (t nil)
  )
)

;; ============================================================
;; КЭШ СВОЙСТВ ДИНАМИЧЕСКИХ БЛОКОВ (Р3.3)
;; Формат: (ename . (has-len has-wid has-hei len-exact len-soft))
;; ============================================================

(if (not (boundp '*su-block-props-cache*))
  (setq *su-block-props-cache* '())
)

(defun su-block-props-cache-clear ()
  (setq *su-block-props-cache* '())
)

(defun su-get-block-props (obj / ent cached dynprops prop pname pval
                               has-len has-wid has-hei len-exact len-soft entry)
  (setq ent (vl-catch-all-apply 'vlax-vla-object->ename (list obj)))

  (if (vl-catch-all-error-p ent)
    '(nil nil nil nil nil)
    (progn
      (setq cached (assoc ent *su-block-props-cache*))
      (if cached
        (cdr cached)
        (progn
          (setq has-len nil has-wid nil has-hei nil
                len-exact nil len-soft nil)

          (setq dynprops
            (vl-catch-all-apply 'vlax-invoke
              (list obj 'GetDynamicBlockProperties)))

          (if (not (vl-catch-all-error-p dynprops))
            (foreach prop dynprops
              (setq pname
                (vl-catch-all-apply 'vla-get-PropertyName (list prop)))
              (if (and (not (vl-catch-all-error-p pname))
                       pname
                       (= (type pname) 'STR))
                (progn
                  (setq pname (strcase (vl-string-trim " \t\r\n" pname)))
                  (cond
                    ((= pname "ДЛИНА")
                     (setq has-len T)
                     (setq pval (vl-catch-all-apply 'vla-get-Value (list prop)))
                     (if (not (vl-catch-all-error-p pval))
                       (setq len-exact (su-value-to-number pval)))
                    )
                    ((and (vl-string-search "ДЛИНА" pname)
                          (not (vl-string-search "ШИРИНА" pname))
                          (not (vl-string-search "ВЫСОТА" pname)))
                     (if (null len-soft)
                       (progn
                         (setq pval (vl-catch-all-apply 'vla-get-Value (list prop)))
                         (if (not (vl-catch-all-error-p pval))
                           (setq len-soft (su-value-to-number pval)))
                       )
                     )
                    )
                  )
                  (if (vl-string-search "ШИРИНА" pname) (setq has-wid T))
                  (if (vl-string-search "ВЫСОТА" pname) (setq has-hei T))
                )
              )
            )
          )

          (setq entry (list has-len has-wid has-hei len-exact len-soft))
          (setq *su-block-props-cache*
            (cons (cons ent entry) *su-block-props-cache*))
          entry
        )
      )
    )
  )
)
;; ============================================================
;; Шаг 9. Признак «нашей» сущности карты раскроя:
;;   - любой объект на служебном слое рамки «Невидимые»;
;;   - INSERT блоков «Раскрой листа …» / «Раскрой …» (карты прошлых запусков).
;; ============================================================
(defun su-map-entity-p (ent / ed typ lay bnm)
  (setq ed (entget ent)
        typ (cdr (assoc 0 ed))
        lay (cdr (assoc 8 ed)))
  (or
    (and lay (= (strcase lay) (strcase "Невидимые")))
    (and (= typ "INSERT")
         (setq bnm (cdr (assoc 2 ed)))
         bnm
         (wcmatch (strcase bnm) "РАСКРОЙ ЛИСТА*,РАСКРОЙ *"))))

;; Удалить карты-артефакты из набора (Шаг 9)
(defun su-ssdel-map-entities (ss / i e)
  (if ss
    (progn
      (setq i -1)
      (repeat (sslength ss)
        (setq i (1+ i) e (ssname ss i))
        (if (and e (su-map-entity-p e)) (ssdel e ss)))
      ss)
    nil))


;; ============================================================
;; Доступ к предвыделению диспетчера. select-utils состояние НЕ меняет
;; (дополнение к Шагу 7): запись выполняет только владелец — extraction.lsp.
;; ============================================================
(defun su-preselection-value (/)
  ;; ТОЛЬКО чтение.
  (if (boundp '*extraction-preselected-set*) *extraction-preselected-set*))

(defun su-take-preselection (/)
  ;; «Взял — погасил»: само погашение делает владелец (ex-take-preselected).
  ;; Если диспетчер не загружен (автономный запуск), просто читаем.
  ;; NB: в AutoLISP нет проверки связанности ФУНКЦИИ — смотрим
  ;; (type sym) = 'SUBR; несвязанный символ вычисляется в nil.
  (if (= (type ex-take-preselected) 'SUBR)
    (ex-take-preselected)
    (su-preselection-value)))

;; ============================================================
;; Выбор вхождений блоков (INSERT) с учетом предвыбора (Р2.2)
;; ============================================================
(defun su-select-inserts (layers / ss i ent data layer out layer-name)
  (su-block-props-cache-clear)
  (setq out '())

  (setq ss (su-take-preselection))
  (if (null ss)
    (setq ss (ssget "_I")))

  (if (null ss)
    (if (null layers)
      (setq ss (ssget "_X" '((0 . "INSERT"))))
      (progn
        (setq layer-name
          (apply 'strcat (mapcar '(lambda (x) (strcat x ",")) layers)))
        (setq layer-name (substr layer-name 1 (1- (strlen layer-name))))
        (setq ss (ssget "_X" (list '(0 . "INSERT") (cons 8 layer-name))))
      )
    )
  )

  (if ss
    (progn
      (setq i 0)
      (repeat (sslength ss)
        (setq ent (ssname ss i))
        (setq data (entget ent))
        (setq layer (cdr (assoc 8 data)))
        (if (and (su-layer-selected-p layer layers) (not (su-map-entity-p ent)))
          (setq out (cons ent out))
        )
        (setq i (1+ i))
      )
    )
  )


  (reverse out)
)

;; ============================================================
;; Защищенное получение EffectiveName
;; ============================================================
(defun su-get-effective-name (obj / r)
  (setq r (vl-catch-all-apply 'vla-get-EffectiveName (list obj)))
  (if (vl-catch-all-error-p r)
    (progn
      (setq r (vl-catch-all-apply 'vla-get-Name (list obj)))
      (if (vl-catch-all-error-p r) nil r)
    )
    r
  )
)

;; ============================================================
;; Получение строкового значения видимости
;; ============================================================
(defun su-get-visibility (obj / dynprops prop pname val result)
  (setq dynprops
    (vl-catch-all-apply 'vlax-invoke (list obj 'GetDynamicBlockProperties)))
  (if (vl-catch-all-error-p dynprops)
    nil
    (progn
      (setq result nil)
      (foreach prop dynprops
        (if (null result)
          (progn
            (setq pname (vl-catch-all-apply 'vla-get-PropertyName (list prop)))
            (if (and (not (vl-catch-all-error-p pname))
                     pname (= (type pname) 'STR)
                     (or (vl-string-search "VISIBILITY" (strcase pname))
                         (vl-string-search "ВИДИМОСТЬ" (strcase pname))))
              (progn
                (setq val (vl-catch-all-apply 'vla-get-Value (list prop)))
                (if (not (vl-catch-all-error-p val))
                  (progn
                    (if (= (type val) 'VARIANT)
                      (setq val (vlax-variant-value val))
                    )
                    (if val (setq result (vl-princ-to-string val)))
                  )
                )
              )
            )
          )
        )
      )
      result
    )
  )
)

;; ============================================================
;; Имя родительского блока для анонимного вхождения
;;
;; После изменения параметров динамический блок живёт как
;; анонимное вхождение *U5385, и EffectiveName у него уже не
;; помогает. Исходное имя достаётся из Block Representation
;; (acdbblockrepbtag) или из XData определения блока: там
;; лежит handle на родительский блок.
;; ============================================================

(defun su-parent-name-by-handle (hdl / ent name)
  (setq ent (handent hdl))
  (if ent
    (setq name (cdr (assoc 2 (entget ent))))
  )
  (if (and name (= (type name) 'STR) (/= name "")
           (/= (substr name 1 1) "*"))
    name
    nil
  )
)

(defun su-anon-parent-name (ent / blk def rep pair found)
  (setq found nil)
  (setq blk (cdr (assoc 2 (entget ent))))
  (if (and blk (= (substr blk 1 1) "*"))
    (progn
      (setq def (tblobjname "BLOCK" blk))
      (if def
        (progn
          ;; 1) Block Representation — так оформлены варианты динамических блоков.
          (setq rep (cdr (assoc -3 (entget def '("ACDBBLOCKREPBTAG")))))
          (if rep
            (progn
              (setq pair (assoc 1005 (cdadr rep)))
              (if pair
                (setq found (su-parent-name-by-handle (cdr pair)))
              )
            )
          )
          ;; 2) Прочие приложения XData: handle на исходный блок.
          (if (not found)
            (progn
              (foreach app (cdr (assoc -3 (entget def '("*"))))
                (if (not found)
                  (progn
                    (foreach pair (cdr app)
                      (if (and (not found) (= (car pair) 1005))
                        (setq found (su-parent-name-by-handle (cdr pair)))
                      )
                    )
                  )
                )
              )
            )
          )
        )
      )
    )
  )
  found
)

;; ============================================================
;; Имя элемента для таблиц (общее для всех задач)
;;
;; su-block-name — имя блока без учёта видимости:
;;   1. EffectiveName, если он не анонимный;
;;   2. анонимное вхождение (*U5385) — имя родительского блока;
;;   3. родителя нет — nil (элемент не показывается).
;;
;; su-element-name — для задач, где видимость задаёт тип элемента:
;;   свойство видимости (Видимость1 / VISIBILITY / ВИДИМОСТЬ),
;;   иначе su-block-name.
;; ============================================================

(defun su-block-name (obj / effname parent)
  (setq effname (su-get-effective-name obj))
  (cond
    ((null effname) "Без имени")
    ((and (= (type effname) 'STR) (/= (substr effname 1 1) "*")) effname)
    ((setq parent (su-anon-parent-name (vlax-vla-object->ename obj)))
      parent)
    (T nil)
  )
)

(defun su-element-name (obj / vis)
  (setq vis (su-get-visibility obj))
  (if (and vis (= (type vis) 'STR) (/= vis ""))
    vis
    (su-block-name obj)
  )
)

;; ============================================================
;; Проверки свойств блоков через кэш (Р3.3)
;; ============================================================

(defun su-is-valid-stock-block (obj / p)
  (setq p (su-get-block-props obj))
  (and (car p) (not (cadr p)) (not (caddr p)))
)

;; ============================================================
;; Имя типа динамического блока (Этап 3.1)
;; ============================================================
(defun su-get-dynblock-type-name (ent / obj vis name)
  (setq obj (vl-catch-all-apply 'vlax-ename->vla-object (list ent)))
  (if (vl-catch-all-error-p obj)
    "Без имени"
    (progn
      (setq vis (vl-catch-all-apply 'su-get-visibility (list obj)))
      (if (or (vl-catch-all-error-p vis) (null vis) (not (= (type vis) 'STR)))
        (setq vis nil)
      )
      (if (and vis (> (strlen (vl-string-trim " \t\r\n" vis)) 0))
        (vl-string-trim " \t\r\n" vis)
        (progn
          (setq name (vl-catch-all-apply 'su-get-effective-name (list obj)))
          (if (or (vl-catch-all-error-p name) (null name)
                  (not (= (type name) 'STR)))
            "Без имени"
            (if (> (strlen (vl-string-trim " \t\r\n" name)) 0)
              (vl-string-trim " \t\r\n" name)
              "Без имени"
            )
          )
        )
      )
    )
  )
)

;; ============================================================
;; Сбор уникальных типов динамических блоков (Этап 3.1)
;; ============================================================
(defun su-collect-dynblock-types (ss filter-fn / i ent typ obj types type-name)
  (setq types '() i 0)
  (if (null ss)
    '()
    (progn
      (repeat (sslength ss)
        (setq ent (ssname ss i))
        (setq typ (cdr (assoc 0 (entget ent))))
        (if (= typ "INSERT")
          (progn
            (setq obj (vl-catch-all-apply 'vlax-ename->vla-object (list ent)))
            (if (not (vl-catch-all-error-p obj))
              (if (or (null filter-fn) (apply filter-fn (list obj)))
                (progn
                  (setq type-name (su-get-dynblock-type-name ent))
                  (if (not (member type-name types))
                    (setq types (cons type-name types))
                  )
                )
              )
            )
          )
        )
        (setq i (1+ i))
      )
      (vl-sort types '(lambda (a b) (< (strcase a) (strcase b))))
    )
  )
)

;; ============================================================
;; Получение длины блока (Р3.2): двухступенчатый поиск из кэша
;; ============================================================
(defun su-get-length (obj candidates / p len)
  (if candidates
    (setq len (su-get-length-by-masks obj candidates))
    (progn
      (setq p (su-get-block-props obj))
      (setq len (if (car p) (nth 3 p) (nth 4 p)))
    )
  )
  (if (numberp len)
    (atoi (rtos len 2 0))
    nil
  )
)

;; ШИРИНА и ВЫСОТА длиной не считаются никогда - ни по точной маске,
;; ни по подстроке. Иначе маска "*" (пользователь хотел «любое свойство»)
;; принесла бы в погонаж ширину: раньше точное совпадение было только
;; с литералом «ДЛИНА», и такой ошибки быть не могло.
(defun su-prop-name-width-height-p (pname)
  (or (vl-string-search "ШИРИНА" pname)
      (vl-string-search "ВЫСОТА" pname))
)

;; Совпадение имени динамического свойства с маской целиком (wcmatch).
(defun su-prop-mask-exact-p (pname masks / found m)
  (if (su-prop-name-width-height-p pname)
    nil
    (progn
      (setq found nil)
      (foreach m masks
        (if (and (= (type m) 'STR)
                 (wcmatch pname (strcase m)))
          (setq found T)
        )
      )
      found
    )
  )
)

;; Мягкое совпадение: маска входит в имя свойства как подстрока.
;; Для умолчания «ДЛИНА» это ловит «ДЛИНА ОБЩАЯ», как раньше.
;; ШИРИНА и ВЫСОТА длиной не считаются никогда.
(defun su-prop-mask-soft-p (pname masks / found m)
  (if (su-prop-name-width-height-p pname)
    nil
    (progn
      (setq found nil)
      (foreach m masks
        (if (and (= (type m) 'STR)
                 (wcmatch pname (strcat "*" (strcase m) "*")))
          (setq found T)
        )
      )
      found
    )
  )
)

;; Длина по маскам имён динамических свойств (настройка input.block.length).
;; Точное совпадение приоритетнее подстроки независимо от порядка свойств
;; в блоке: «Длина» важнее «Длина хвоста».
(defun su-get-length-by-masks (obj masks / dynprops prop pname pval exact soft)
  (setq dynprops
    (vl-catch-all-apply 'vlax-invoke
      (list obj 'GetDynamicBlockProperties)))
  (if (vl-catch-all-error-p dynprops)
    nil
    (progn
      (setq exact nil soft nil)
      (foreach prop dynprops
        (setq pname
          (vl-catch-all-apply 'vla-get-PropertyName (list prop)))
        (if (and (not (vl-catch-all-error-p pname))
                 pname
                 (= (type pname) 'STR))
          (progn
            (setq pname (strcase (vl-string-trim " \t\r\n" pname)))
            ;; Значение читается только у подходящего свойства:
            ;; ActiveX-вызов на каждое свойство блока — лишняя работа.
            (if (and (null exact) (su-prop-mask-exact-p pname masks))
              (progn
                (setq pval
                  (vl-catch-all-apply 'vla-get-Value (list prop)))
                (if (not (vl-catch-all-error-p pval))
                  (setq exact (su-value-to-number pval))
                )
              )
            )
            (if (and (null soft) (su-prop-mask-soft-p pname masks))
              (progn
                (setq pval
                  (vl-catch-all-apply 'vla-get-Value (list prop)))
                (if (not (vl-catch-all-error-p pval))
                  (setq soft (su-value-to-number pval))
                )
              )
            )
          )
        )
      )
      (if exact exact soft)
    )
  )
)

;; ============================================================
;; MLINE: вершины из DXF 11 (M2.1 — без ActiveX)
;; ============================================================
(defun su-mline-vertices (ent / out)
  (setq out '())
  (foreach g (entget ent)
    (if (= (car g) 11)
      (setq out (cons (cdr g) out))
    )
  )
  (reverse out)
)

(defun su-mline-vertex-count (ent / n)
  (setq n 0)
  (foreach g (entget ent)
    (if (= (car g) 11) (setq n (1+ n)))
  )
  n
)

;; ============================================================
;; MLINE: тип = имя MLINESTYLE (DXF 2)
;; ============================================================
(defun su-mline-style-name (ent / d v)
  (setq d (entget ent))
  (if (null d)
    nil
    (progn
      (setq v (cdr (assoc 2 d)))
      (if (and v (= (type v) 'STR) (> (strlen (vl-string-trim " \t\r\n" v)) 0))
        (vl-string-trim " \t\r\n" v)
        nil
      )
    )
  )
)

(defun su-mline-type-name (ent / n)
  (setq n (su-mline-style-name ent))
  (if n n "Без имени")
)

(defun su-collect-mline-types (ss / i ent typ types)
  (setq types '() i 0)
  (if (null ss)
    '()
    (progn
      (repeat (sslength ss)
        (setq ent (ssname ss i))
        (if (= (cdr (assoc 0 (entget ent))) "MLINE")
          (progn
            (setq typ (su-mline-type-name ent))
            (if (not (member typ types))
              (setq types (cons typ types))
            )
          )
        )
        (setq i (1+ i))
      )
      (vl-sort types '(lambda (a b) (< (strcase a) (strcase b))))
    )
  )
)

(defun su-count-mline-by-type (ss type-name / i ent n count)
  (setq count 0 i 0)
  (if (null ss)
    0
    (progn
      (repeat (sslength ss)
        (setq ent (ssname ss i))
        (if (= (cdr (assoc 0 (entget ent))) "MLINE")
          (if (or (null type-name) (= type-name ""))
            (setq count (1+ count))
            (progn
              (setq n (su-mline-type-name ent))
              (if (= n type-name) (setq count (1+ count)))
            )
          )
        )
        (setq i (1+ i))
      )
      count
    )
  )
)

;; ============================================================
;; MLINE: допуск осевого выравнивания и геометрия для раскроя
;; ============================================================
(if (not (boundp '*SU-MLINE-AXIS-TOL*))
  (setq *SU-MLINE-AXIS-TOL* 0.01)
)

(defun su-mline-cut-geom (ent / v p1 p2 dx dy tol)
  (setq v (su-mline-vertices ent))
  (if (/= (length v) 2)
    nil
    (progn
      (setq p1 (car v) p2 (cadr v))
      (setq dx (abs (- (car p2) (car p1)))
            dy (abs (- (cadr p2) (cadr p1)))
            tol *SU-MLINE-AXIS-TOL*)
      (cond
        ((<= dy tol) (cons (distance p1 p2) 'H))
        ((<= dx tol) (cons (distance p1 p2) 'V))
        (T nil)
      )
    )
  )
)

;; ============================================================
;; Проверка соответствия слоя списку (с масками)
;; ============================================================
(defun su-layer-match-any (layer layers / found)
  (if (or (null layers) (not (listp layers)) (= (length layers) 0))
    T
    (progn
      (setq found nil)
      (foreach l layers
        (if (and (= (type l) 'STR)
                 (wcmatch (strcase layer) (strcase l)))
          (setq found T)
        )
      )
      found
    )
  )
)

(defun su-entity-layer-matches-p (ent layers / data layer)
  (setq data (if ent (entget ent) nil)
        layer (if data (cdr (assoc 8 data)) nil))
  (and layer (su-layer-match-any layer layers))
)

(defun su-block-values-match-p (values masks / found value mask)
  (if (or (null masks) (not (listp masks)) (= (length masks) 0))
    T
    (progn
      (setq found nil)
      (foreach value values
        (if (and (= (type value) 'STR) (> (strlen value) 0))
          (foreach mask masks
            (if (and (= (type mask) 'STR)
                     (wcmatch (strcase value) (strcase mask)))
              (setq found T)
            )
          )
        )
      )
      found
    )
  )
)

(defun su-block-matches-name-masks-p (ent masks / obj name vis values)
  (if (null ent)
    nil
    (progn
      (setq obj (vl-catch-all-apply 'vlax-ename->vla-object (list ent)))
      (if (vl-catch-all-error-p obj)
        nil
        (progn
          (setq name (vl-catch-all-apply 'su-get-effective-name (list obj)))
          (if (vl-catch-all-error-p name) (setq name nil))
          (setq vis (vl-catch-all-apply 'su-get-visibility (list obj)))
          (if (vl-catch-all-error-p vis) (setq vis nil))
          (setq values '())
          (if (= (type name) 'STR) (setq values (cons name values)))
          (if (= (type vis) 'STR) (setq values (cons vis values)))
          (su-block-values-match-p values masks)
        )
      )
    )
  )
)

(defun su-filter-inserts-by-name-masks (inserts masks / out ent)
  (setq out '())
  (foreach ent inserts
    (if (su-block-matches-name-masks-p ent masks)
      (setq out (cons ent out))
    )
  )
  (reverse out)
)

(defun su-filter-ss-by-block-name-masks (ss masks / i ent typ out)
  ;; Filter only INSERT entities; geometry entities remain untouched.
  (if (null ss)
    nil
    (progn
      (setq out (ssadd) i 0)
      (repeat (sslength ss)
        (setq ent (ssname ss i)
              typ (cdr (assoc 0 (entget ent))))
        (if (or (not (= typ "INSERT"))
                (su-block-matches-name-masks-p ent masks))
          (ssadd ent out))
        (setq i (1+ i))
      )
      (if (> (sslength out) 0) out nil)
    )
  )
)

;; ============================================================
;; Типы объектов, допустимые в CUTLINE
;; ============================================================
(setq *su-cutline-types* '("LINE" "MLINE" "INSERT"))

;; ============================================================
;; Ручная фильтрация selection set по типу и слоям
;; ============================================================
(defun su-filter-ss-cutline (ss types layers / i ent data typ lay new-ss)
  (if (null ss)
    nil
    (progn
      (setq new-ss (ssadd))
      (setq i 0)
      (repeat (sslength ss)
        (setq ent (ssname ss i))
        (setq data (entget ent))
        (setq typ (cdr (assoc 0 data)))
        (setq lay (cdr (assoc 8 data)))
        (if (and (member typ types) (su-layer-match-any lay layers) (not (su-map-entity-p ent)))
          (ssadd ent new-ss)
        )
        (setq i (1+ i))
      )
      (if (> (sslength new-ss) 0) new-ss nil)
    )
  )
)

;; ============================================================
;; Пост-фильтрация динамических блоков для раскроя
;; ============================================================
(defun su-filter-dynblocks (ss / i ent typ obj new-ss)
  (if (null ss)
    nil
    (progn
      (setq new-ss (ssadd))
      (setq i 0)
      (repeat (sslength ss)
        (setq ent (ssname ss i))
        (setq typ (cdr (assoc 0 (entget ent))))
        (cond
          ((or (= typ "LINE") (= typ "MLINE"))
           (ssadd ent new-ss)
          )
          ((= typ "INSERT")
           (setq obj (vl-catch-all-apply 'vlax-ename->vla-object (list ent)))
           (if (and (not (vl-catch-all-error-p obj))
                    (su-is-valid-stock-block obj))
             (ssadd ent new-ss)
           )
          )
        )
        (setq i (1+ i))
      )
      (if (> (sslength new-ss) 0) new-ss nil)
    )
  )
)

;; ============================================================
;; Построение ssget-фильтра для CUTLINE
;; ============================================================
(defun su-build-cutline-ssfilter (layers / base layer-mask)
  (setq base (list '(0 . "LINE,MLINE,INSERT")))
  (if (and layers (listp layers) (> (length layers) 0))
    (progn
      (setq layer-mask
        (apply 'strcat (mapcar '(lambda (x) (strcat x ",")) layers)))
      (setq layer-mask (substr layer-mask 1 (1- (strlen layer-mask))))
      (append base (list (cons 8 layer-mask)))
    )
    base
  )
)

;; ============================================================
;; Извлечение исходного набора объектов для CUTLINE (Р2.2)
;; ============================================================
(defun su-select-cutline-objects (layers / ss ssfilter raw-count pre-ss)
  (if (and (null layers) (= (type ae-settings-task-layers) 'SUBR))
    (setq layers (ae-settings-task-layers 'CUTLINE)))
  (su-block-props-cache-clear)
  (setq ss nil)
  (setq ssfilter (su-build-cutline-ssfilter layers))

  (setq pre-ss (su-take-preselection))
  (if pre-ss
    (progn
      (setq ss (su-filter-ss-cutline pre-ss *su-cutline-types* layers))
      (if (not (and ss (> (sslength ss) 0)))
        (setq ss nil)
      )
    )
  )

  (if (null ss)
    (setq ss (ssget "_I" ssfilter))
  )

  (if (null ss)
    (setq ss (ssget ssfilter))
  )

  (if ss
    (progn
      (setq raw-count (sslength ss))
      (setq ss (su-filter-dynblocks ss))
      (if (and ss (= (type ae-settings-task-blocks) 'SUBR))
        (setq ss
          (su-filter-ss-by-block-name-masks
            ss (ae-settings-task-blocks 'CUTLINE))))
      (if ss (setq ss (su-ssdel-map-entities ss)))
      (if (and ss raw-count (< (sslength ss) raw-count))
        (princ (strcat "\n  После пост-фильтрации отсеяно: "
                       (itoa (- raw-count (sslength ss)))
                       " непригодных объектов (динамические блоки без свойства 'Длина' или с 'Ширина'/'Высота')"))
      )
    )
  )

  ss
)

;; ============================================================
;; ВЫБОР LWPOLYLINE С УЧЕТОМ СЛОЕВ (Облицовка, К1)
;; ============================================================
(defun su-select-lwpolylines (layers / ss out i ent data layer layer-mask)
  (setq out '())

  (setq ss (su-take-preselection))
  (if (null ss)
    (setq ss (ssget "_I")))

  (if (null ss)
    (if (null layers)
      (setq ss (ssget "_X" '((0 . "LWPOLYLINE"))))
      (progn
        (setq layer-mask
          (apply 'strcat (mapcar '(lambda (x) (strcat x ",")) layers)))
        (setq layer-mask (substr layer-mask 1 (1- (strlen layer-mask))))
        (setq ss (ssget "_X" (list '(0 . "LWPOLYLINE") (cons 8 layer-mask))))
      )
    )
  )

  (if ss
    (progn
      (setq i 0)
      (repeat (sslength ss)
        (setq ent (ssname ss i))
        (setq data (entget ent))
        (setq layer (cdr (assoc 8 data)))
        (if (and (su-layer-selected-p layer layers) (not (su-map-entity-p ent)))
          (setq out (cons ent out))
        )
        (setq i (1+ i))
      )
    )
  )


  (reverse out)
)

;; ============================================================
;; АЛИАС для совместимости со старыми вызовами других модулей
;; ============================================================
(if (not (= (type su_layer_selected-p) 'SUBR))
  (defun su_layer_selected-p (layer layers)
    (su-layer-selected-p layer layers)
  )
)

;; SELECT-UTILS.LSP загружен (ред. 5: длина блока по маскам свойств из настроек).
(princ)
