;;; ============================================================
;;; common/excel-utils.lsp
;;; Экспорт отчетов в Excel (XML Spreadsheet) и CSV
;;; Функции для Фасонки, Подсистемы и Заполнения
;;; ============================================================

(vl-load-com)

;; ------------------------------------------------------------
;; Экранирование XML-спецсимволов
;; ------------------------------------------------------------
(defun eu-xml-escape (str / result ch)
  (setq result "")
  (while (/= str "")
    (setq ch (substr str 1 1))
    (cond
      ((= ch "&") (setq result (strcat result "&amp;")))
      ((= ch "<") (setq result (strcat result "&lt;")))
      ((= ch ">") (setq result (strcat result "&gt;")))
      ((= ch "\"") (setq result (strcat result "&quot;")))
      ((= ch "'") (setq result (strcat result "&apos;")))
      (t (setq result (strcat result ch)))
    )
    (setq str (substr str 2))
  )
  result
)

;; ------------------------------------------------------------
;; Экранирование текстового значения для CSV
;; Заключает в кавычки, если есть точка с запятой, кавычка или перевод строки
;; Внутренние кавычки удваиваются
;; ------------------------------------------------------------
(defun eu-csv-quote (str / result)
  (if (null str)
    ""
    (if (or (vl-string-search ";" str)
            (vl-string-search "\"" str)
            (vl-string-search "\n" str))
      (progn
        (setq result (vl-string-subst "\"\"" "\"" str))
        (strcat "\"" result "\"")
      )
      str
    )
  )
)

;; ------------------------------------------------------------
;; Генерация блока XML-стилей для Excel
;; num-format: "0.00" для Фасонки/Подсистемы, "0.##" для Заполнения
;; Возвращает строку с полным блоком <Styles>...</Styles>
;; ------------------------------------------------------------
(defun eu-xml-styles (num-format / styles)
  (setq styles
    (strcat
      " <Styles>\n"
      "  <Style ss:ID=\"Default\" ss:Name=\"Normal\">\n"
      "   <Alignment ss:Vertical=\"Center\"/>\n"
      "  </Style>\n"
      "  <Style ss:ID=\"Data\">\n"
      "   <Alignment ss:Vertical=\"Center\"/>\n"
      "   <Borders>\n"
      "    <Border ss:Position=\"Bottom\" ss:LineStyle=\"Continuous\" ss:Weight=\"1\"/>\n"
      "    <Border ss:Position=\"Left\" ss:LineStyle=\"Continuous\" ss:Weight=\"1\"/>\n"
      "    <Border ss:Position=\"Right\" ss:LineStyle=\"Continuous\" ss:Weight=\"1\"/>\n"
      "    <Border ss:Position=\"Top\" ss:LineStyle=\"Continuous\" ss:Weight=\"1\"/>\n"
      "   </Borders>\n"
      "  </Style>\n"
      "  <Style ss:ID=\"Header\">\n"
      "   <Font ss:Bold=\"1\" ss:Size=\"12\" ss:Underline=\"Single\"/>\n"
      "   <Interior ss:Color=\"#D9D9D9\" ss:Pattern=\"Solid\"/>\n"
      "   <Alignment ss:Horizontal=\"Center\" ss:Vertical=\"Center\"/>\n"
      "   <Borders>\n"
      "    <Border ss:Position=\"Bottom\" ss:LineStyle=\"Continuous\" ss:Weight=\"1\"/>\n"
      "    <Border ss:Position=\"Left\" ss:LineStyle=\"Continuous\" ss:Weight=\"1\"/>\n"
      "    <Border ss:Position=\"Right\" ss:LineStyle=\"Continuous\" ss:Weight=\"1\"/>\n"
      "    <Border ss:Position=\"Top\" ss:LineStyle=\"Continuous\" ss:Weight=\"1\"/>\n"
      "   </Borders>\n"
      "  </Style>\n"
      "  <Style ss:ID=\"BoldUnderline\">\n"
      "   <Font ss:Bold=\"1\" ss:Underline=\"Single\"/>\n"
      "   <Interior ss:Color=\"#D9D9D9\" ss:Pattern=\"Solid\"/>\n"
      "   <Alignment ss:Horizontal=\"Center\" ss:Vertical=\"Center\"/>\n"
      "   <Borders>\n"
      "    <Border ss:Position=\"Bottom\" ss:LineStyle=\"Continuous\" ss:Weight=\"1\"/>\n"
      "    <Border ss:Position=\"Left\" ss:LineStyle=\"Continuous\" ss:Weight=\"1\"/>\n"
      "    <Border ss:Position=\"Right\" ss:LineStyle=\"Continuous\" ss:Weight=\"1\"/>\n"
      "    <Border ss:Position=\"Top\" ss:LineStyle=\"Continuous\" ss:Weight=\"1\"/>\n"
      "   </Borders>\n"
      "  </Style>\n"
      "  <Style ss:ID=\"BoldUnderlineNum\">\n"
      "   <Font ss:Bold=\"1\" ss:Underline=\"Single\"/>\n"
      "   <Interior ss:Color=\"#D9D9D9\" ss:Pattern=\"Solid\"/>\n"
      "   <NumberFormat ss:Format=\"" num-format "\"/>\n"
      "   <Alignment ss:Horizontal=\"Center\" ss:Vertical=\"Center\"/>\n"
      "   <Borders>\n"
      "    <Border ss:Position=\"Bottom\" ss:LineStyle=\"Continuous\" ss:Weight=\"1\"/>\n"
      "    <Border ss:Position=\"Left\" ss:LineStyle=\"Continuous\" ss:Weight=\"1\"/>\n"
      "    <Border ss:Position=\"Right\" ss:LineStyle=\"Continuous\" ss:Weight=\"1\"/>\n"
      "    <Border ss:Position=\"Top\" ss:LineStyle=\"Continuous\" ss:Weight=\"1\"/>\n"
      "   </Borders>\n"
      "  </Style>\n"
      "  <Style ss:ID=\"Num\">\n"
      "   <NumberFormat ss:Format=\"" num-format "\"/>\n"
      "   <Borders>\n"
      "    <Border ss:Position=\"Bottom\" ss:LineStyle=\"Continuous\" ss:Weight=\"1\"/>\n"
      "    <Border ss:Position=\"Left\" ss:LineStyle=\"Continuous\" ss:Weight=\"1\"/>\n"
      "    <Border ss:Position=\"Right\" ss:LineStyle=\"Continuous\" ss:Weight=\"1\"/>\n"
      "    <Border ss:Position=\"Top\" ss:LineStyle=\"Continuous\" ss:Weight=\"1\"/>\n"
      "   </Borders>\n"
      "  </Style>\n"
      " </Styles>"))
  styles
)

;; ============================================================
;; ФУНКЦИИ ДЛЯ ФАСОНКИ (восстановлены полностью)
;; ============================================================

(defun eu-export-xls-detail (data xlsfile / f rowNum groupIndex name recs rec itemNum len count startRow endRow sum totalSum)
  (setq f (open xlsfile "w"))
  (if (null f)
    nil
    (progn
      ;; Заголовок XML и стили
      (write-line "<?xml version=\"1.0\" encoding=\"windows-1251\"?>" f)
      (write-line "<?mso-application progid=\"Excel.Sheet\"?>" f)
      (write-line "<Workbook xmlns=\"urn:schemas-microsoft-com:office:spreadsheet\"" f)
      (write-line " xmlns:o=\"urn:schemas-microsoft-com:office:office\"" f)
      (write-line " xmlns:x=\"urn:schemas-microsoft-com:office:excel\"" f)
      (write-line " xmlns:ss=\"urn:schemas-microsoft-com:office:spreadsheet\"" f)
      (write-line " xmlns:html=\"http://www.w3.org/TR/REC-html40\">" f)
      (write-line (eu-xml-styles "0.00") f)

      (write-line " <Worksheet ss:Name=\"Lengths\">" f)
      (write-line "  <Table>" f)
      (write-line "   <Column ss:Width=\"30\"/>" f)
      (write-line "   <Column ss:Width=\"200\"/>" f)
      (write-line "   <Column ss:Width=\"75\"/>" f)
      (write-line "   <Column ss:Width=\"75\"/>" f)
      (write-line "   <Column ss:Width=\"75\"/>" f)

      (write-line "   <Row ss:Height=\"20\">" f)
      (write-line "    <Cell ss:StyleID=\"Header\" ss:MergeAcross=\"4\"><Data ss:Type=\"String\">Фасонное железо</Data></Cell>" f)
      (write-line "   </Row>" f)

      (write-line "   <Row>" f)
      (write-line "    <Cell ss:StyleID=\"Header\"><Data ss:Type=\"String\">№</Data></Cell>" f)
      (write-line "    <Cell ss:StyleID=\"Header\"><Data ss:Type=\"String\">Тип фасонки</Data></Cell>" f)
      (write-line "    <Cell ss:StyleID=\"Header\"><Data ss:Type=\"String\">Длина, мм</Data></Cell>" f)
      (write-line "    <Cell ss:StyleID=\"Header\"><Data ss:Type=\"String\">Кол-во, шт.</Data></Cell>" f)
      (write-line "    <Cell ss:StyleID=\"Header\"><Data ss:Type=\"String\">Сумма, м.п.</Data></Cell>" f)
      (write-line "   </Row>" f)

      (setq rowNum 3)
      (foreach ig data
        (setq groupIndex (car ig)
              name       (cadr ig)
              recs       (caddr ig)
              startRow   rowNum
              itemNum    0
              totalSum   0.0)

        (foreach rec recs
          (setq itemNum (1+ itemNum)
                len     (cadr rec)
                count   (caddr rec)
                sum     (/ (* len count) 1000.0)
                totalSum (+ totalSum sum))

          (write-line "   <Row>" f)
          (write-line (strcat "    <Cell ss:StyleID=\"Data\"><Data ss:Type=\"String\">" (itoa groupIndex) "." (itoa itemNum) "</Data></Cell>") f)
          (write-line (strcat "    <Cell ss:StyleID=\"Data\"><Data ss:Type=\"String\">" (eu-xml-escape name) "</Data></Cell>") f)
          (write-line (strcat "    <Cell ss:StyleID=\"Data\"><Data ss:Type=\"Number\">" (rtos len 2 0) "</Data></Cell>") f)
          (write-line (strcat "    <Cell ss:StyleID=\"Data\"><Data ss:Type=\"Number\">" (itoa count) "</Data></Cell>") f)
          (write-line (strcat "    <Cell ss:StyleID=\"Num\" ss:Formula=\"=RC[-2]*RC[-1]/1000\"><Data ss:Type=\"Number\">" (rtos sum 2 2) "</Data></Cell>") f)
          (write-line "   </Row>" f)

          (setq rowNum (1+ rowNum))
        )

        (setq endRow (1- rowNum))
        (write-line "   <Row>" f)
        (write-line (strcat "    <Cell ss:StyleID=\"BoldUnderline\"><Data ss:Type=\"String\">" (itoa groupIndex) "</Data></Cell>") f)
        (write-line (strcat "    <Cell ss:StyleID=\"BoldUnderline\"><Data ss:Type=\"String\">" (eu-xml-escape name) "</Data></Cell>") f)
        (write-line "    <Cell ss:StyleID=\"BoldUnderline\"><Data ss:Type=\"String\"></Data></Cell>" f)
        (write-line "    <Cell ss:StyleID=\"BoldUnderline\"><Data ss:Type=\"String\"></Data></Cell>" f)
        (write-line (strcat "    <Cell ss:StyleID=\"BoldUnderlineNum\" ss:Formula=\"=SUM(R" (itoa startRow) "C5:R" (itoa endRow) "C5)\"><Data ss:Type=\"Number\">" (rtos totalSum 2 2) "</Data></Cell>") f)
        (write-line "   </Row>" f)

        (setq rowNum (1+ rowNum))
      )

      (write-line "  </Table>" f)
      (write-line " </Worksheet>" f)
      (write-line "</Workbook>" f)
      (close f)
      T
    )
  )
)

(defun eu-export-xls-summary (data xlsfile / f rowNum i totalCount totalSum)
  (setq f (open xlsfile "w"))
  (if (null f)
    nil
    (progn
      (write-line "<?xml version=\"1.0\" encoding=\"windows-1251\"?>" f)
      (write-line "<?mso-application progid=\"Excel.Sheet\"?>" f)
      (write-line "<Workbook xmlns=\"urn:schemas-microsoft-com:office:spreadsheet\"" f)
      (write-line " xmlns:o=\"urn:schemas-microsoft-com:office:office\"" f)
      (write-line " xmlns:x=\"urn:schemas-microsoft-com:office:excel\"" f)
      (write-line " xmlns:ss=\"urn:schemas-microsoft-com:office:spreadsheet\"" f)
      (write-line " xmlns:html=\"http://www.w3.org/TR/REC-html40\">" f)
      (write-line (eu-xml-styles "0.00") f)
      (write-line " <Worksheet ss:Name=\"Summary\">" f)
      (write-line "  <Table>" f)
      (write-line "   <Column ss:Width=\"30\"/>" f)
      (write-line "   <Column ss:Width=\"200\"/>" f)
      (write-line "   <Column ss:Width=\"75\"/>" f)
      (write-line "   <Column ss:Width=\"75\"/>" f)
      (write-line "   <Row ss:Height=\"20\">" f)
      (write-line "    <Cell ss:StyleID=\"Header\" ss:MergeAcross=\"3\"><Data ss:Type=\"String\">Фасонное железо</Data></Cell>" f)
      (write-line "   </Row>" f)
      (write-line "   <Row>" f)
      (write-line "    <Cell ss:StyleID=\"Header\"><Data ss:Type=\"String\">№</Data></Cell>" f)
      (write-line "    <Cell ss:StyleID=\"Header\"><Data ss:Type=\"String\">Тип фасонки</Data></Cell>" f)
      (write-line "    <Cell ss:StyleID=\"Header\"><Data ss:Type=\"String\">Кол-во, шт.</Data></Cell>" f)
      (write-line "    <Cell ss:StyleID=\"Header\"><Data ss:Type=\"String\">Сумма, м.п.</Data></Cell>" f)
      (write-line "   </Row>" f)

      (setq rowNum 3
            i 0)
      (foreach rec data
        (setq i (1+ i)
              name  (car rec)
              count (cadr rec)
              sum   (caddr rec))
        (write-line "   <Row>" f)
        (write-line (strcat "    <Cell ss:StyleID=\"Data\"><Data ss:Type=\"Number\">" (itoa i) "</Data></Cell>") f)
        (write-line (strcat "    <Cell ss:StyleID=\"Data\"><Data ss:Type=\"String\">" (eu-xml-escape name) "</Data></Cell>") f)
        (write-line (strcat "    <Cell ss:StyleID=\"Data\"><Data ss:Type=\"Number\">" (itoa count) "</Data></Cell>") f)
        (write-line (strcat "    <Cell ss:StyleID=\"Data\"><Data ss:Type=\"Number\">" (rtos sum 2 2) "</Data></Cell>") f)
        (write-line "   </Row>" f)
        (setq rowNum (1+ rowNum))
      )

      ;; Итоговая строка
      (setq totalCount 0
            totalSum   0.0)
      (foreach rec data
        (setq totalCount (+ totalCount (cadr rec))
              totalSum   (+ totalSum (caddr rec)))
      )
      (write-line "   <Row>" f)
      (write-line "    <Cell ss:StyleID=\"BoldUnderline\" ss:MergeAcross=\"1\"><Data ss:Type=\"String\">Итого</Data></Cell>" f)
      (write-line (strcat "    <Cell ss:StyleID=\"BoldUnderline\"><Data ss:Type=\"Number\">" (itoa totalCount) "</Data></Cell>") f)
      (write-line (strcat "    <Cell ss:StyleID=\"BoldUnderline\"><Data ss:Type=\"Number\">" (rtos totalSum 2 2) "</Data></Cell>") f)
      (write-line "   </Row>" f)

      (write-line "  </Table>" f)
      (write-line " </Worksheet>" f)
      (write-line "</Workbook>" f)
      (close f)
      T
    )
  )
)

;; ------------------------------------------------------------
;; Экспорт Фасонка DETAIL в CSV
;; Разделитель: точка с запятой (единообразно с Подсистемой)
;; Десятичный разделитель: запятая
;; data: список (номер-группы имя-группы список-записей)
;;   где запись: (номер длина количество)
;; ------------------------------------------------------------
(defun eu-export-csv-detail (data csvfile / f groupIndex name recs rec itemNum len count sum)
  (setq f (open csvfile "w"))
  (if f
    (progn
      (write-line "Фасонное железо" f)
      (write-line "№;Тип фасонки;Длина, мм;Кол-во, шт.;Сумма, м.п." f)

      (foreach ig data
        (setq groupIndex (car ig)
              name       (cadr ig)
              recs       (caddr ig)
              itemNum    0)

        (foreach rec recs
          (setq itemNum (1+ itemNum)
                len     (cadr rec)
                count   (caddr rec)
                sum     (/ (* len count) 1000.0))

          (write-line
            (strcat (itoa groupIndex) "-" (itoa itemNum) ";"   ; ? дефис здесь
                    (eu-csv-quote name) ";"
                    (rtos len 2 0) ";"
                    (itoa count) ";"
                    "\"" (vl-string-translate "." "," (rtos sum 2 2)) "\"")
            f)
        )
      )

      (close f)
      T
    )
    nil
  )
)

;; ------------------------------------------------------------
;; Экспорт Фасонка SUMMARY в CSV
;; Разделитель: точка с запятой (единообразно с Подсистемой)
;; Десятичный разделитель: запятая
;; data: список (имя количество сумма)
;; ------------------------------------------------------------
(defun eu-export-csv-summary (data csvfile / f i name count sum totalCount totalSum)
  (setq f (open csvfile "w"))
  (if f
    (progn
      (write-line "Фасонное железо" f)
      (write-line "№;Тип фасонки;Кол-во, шт.;Сумма, м.п." f)

      (setq i 0 totalCount 0 totalSum 0.0)
      (foreach rec data
        (setq i (1+ i)
              name  (car rec)
              count (cadr rec)
              sum   (caddr rec))
        (setq totalCount (+ totalCount count)
              totalSum   (+ totalSum sum))

        (write-line
          (strcat (itoa i) ";"
                  (eu-csv-quote name) ";"
                  (itoa count) ";"
                  "\"" (vl-string-translate "." "," (rtos sum 2 2)) "\"")
            f)
      )

      ;; Итоговая строка
      (write-line
        (strcat "Итого по всем позициям:;;"
                (itoa totalCount) ";"
                "\"" (vl-string-translate "." "," (rtos totalSum 2 2)) "\"")
        f)

      (close f)
      T
    )
    nil
  )
)

;; ============================================================
;; ФУНКЦИИ ДЛЯ ПОДСИСТЕМЫ
;; ============================================================

(defun eu-export-subsystem-detail (data xlsfile / f rowNum i name len cnt sum
                                    totalSum groupIndex itemNum groupName groupRows startRow endRow)
  (setq f (open xlsfile "w"))
  (if (null f)
    nil
    (progn
      (write-line "<?xml version=\"1.0\" encoding=\"windows-1251\"?>" f)
      (write-line "<?mso-application progid=\"Excel.Sheet\"?>" f)
      (write-line "<Workbook xmlns=\"urn:schemas-microsoft-com:office:spreadsheet\"" f)
      (write-line " xmlns:o=\"urn:schemas-microsoft-com:office:office\"" f)
      (write-line " xmlns:x=\"urn:schemas-microsoft-com:office:excel\"" f)
      (write-line " xmlns:ss=\"urn:schemas-microsoft-com:office:spreadsheet\"" f)
      (write-line " xmlns:html=\"http://www.w3.org/TR/REC-html40\">" f)
      (write-line (eu-xml-styles "0.00") f)

      (write-line " <Worksheet ss:Name=\"SubsystemDetail\">" f)
      (write-line "  <Table>" f)
      (write-line "   <Column ss:Width=\"30\"/>" f)
      (write-line "   <Column ss:Width=\"250\"/>" f)
      (write-line "   <Column ss:Width=\"75\"/>" f)
      (write-line "   <Column ss:Width=\"75\"/>" f)
      (write-line "   <Column ss:Width=\"75\"/>" f)

      (write-line "   <Row ss:Height=\"20\">" f)
      (write-line "    <Cell ss:StyleID=\"Header\" ss:MergeAcross=\"4\"><Data ss:Type=\"String\">Подсистема</Data></Cell>" f)
      (write-line "   </Row>" f)

      (write-line "   <Row>" f)
      (write-line "    <Cell ss:StyleID=\"Header\"><Data ss:Type=\"String\">№</Data></Cell>" f)
      (write-line "    <Cell ss:StyleID=\"Header\"><Data ss:Type=\"String\">Наименование</Data></Cell>" f)
      (write-line "    <Cell ss:StyleID=\"Header\"><Data ss:Type=\"String\">Длина, мм</Data></Cell>" f)
      (write-line "    <Cell ss:StyleID=\"Header\"><Data ss:Type=\"String\">Кол-во, шт.</Data></Cell>" f)
      (write-line "    <Cell ss:StyleID=\"Header\"><Data ss:Type=\"String\">Сумма, м.п.</Data></Cell>" f)
      (write-line "   </Row>" f)

      (setq rowNum 3
            itemNum 0)

      ;; Штучные блоки
      (foreach rec data
        (setq name (car rec)
              len  (cadr rec)
              cnt  (caddr rec))
        (if (null len)
          (progn
            (setq itemNum (1+ itemNum))
            (write-line "   <Row>" f)
            (write-line (strcat "    <Cell ss:StyleID=\"Data\"><Data ss:Type=\"Number\">" (itoa itemNum) "</Data></Cell>") f)
            (write-line (strcat "    <Cell ss:StyleID=\"Data\"><Data ss:Type=\"String\">" (eu-xml-escape name) "</Data></Cell>") f)
            (write-line "    <Cell ss:StyleID=\"Data\"><Data ss:Type=\"String\"></Data></Cell>" f)
            (write-line (strcat "    <Cell ss:StyleID=\"Data\"><Data ss:Type=\"Number\">" (itoa cnt) "</Data></Cell>") f)
            (write-line "    <Cell ss:StyleID=\"Data\"><Data ss:Type=\"String\"></Data></Cell>" f)
            (write-line "   </Row>" f)
            (setq rowNum (1+ rowNum))
          )
        )
      )

      ;; Мерные блоки: группировка по наименованию
      (setq groups '())
      (foreach rec data
        (if (cadr rec)
          (if (not (assoc (car rec) groups))
            (setq groups (cons (list (car rec)) groups))
          )
        )
      )
      (setq groups (vl-sort groups '(lambda (a b) (< (car a) (car b)))))

      (foreach grp groups
        (setq groupName (car grp)
              groupRows '()
              totalSum 0.0
              startRow rowNum)
        (foreach rec data
          (if (and (= (car rec) groupName) (cadr rec))
            (setq groupRows (append groupRows (list rec)))
          )
        )
        (foreach rec groupRows
          (setq len (cadr rec)
                cnt (caddr rec)
                sum (/ (* len cnt) 1000.0)
                totalSum (+ totalSum sum))
          (setq itemNum (1+ itemNum))
          (write-line "   <Row>" f)
          (write-line (strcat "    <Cell ss:StyleID=\"Data\"><Data ss:Type=\"Number\">" (itoa itemNum) "</Data></Cell>") f)
          (write-line (strcat "    <Cell ss:StyleID=\"Data\"><Data ss:Type=\"String\">" (eu-xml-escape groupName) "</Data></Cell>") f)
          (write-line (strcat "    <Cell ss:StyleID=\"Data\"><Data ss:Type=\"Number\">" (rtos len 2 0) "</Data></Cell>") f)
          (write-line (strcat "    <Cell ss:StyleID=\"Data\"><Data ss:Type=\"Number\">" (itoa cnt) "</Data></Cell>") f)
          (write-line (strcat "    <Cell ss:StyleID=\"Num\" ss:Formula=\"=RC[-2]*RC[-1]/1000\"><Data ss:Type=\"Number\">" (rtos sum 2 2) "</Data></Cell>") f)
          (write-line "   </Row>" f)
          (setq rowNum (1+ rowNum))
        )
        (setq endRow (1- rowNum))
        (write-line "   <Row>" f)
        (write-line "    <Cell ss:StyleID=\"BoldUnderline\"><Data ss:Type=\"String\"></Data></Cell>" f)
        (write-line (strcat "    <Cell ss:StyleID=\"BoldUnderline\"><Data ss:Type=\"String\">" (eu-xml-escape groupName) "</Data></Cell>") f)
        (write-line "    <Cell ss:StyleID=\"BoldUnderline\"><Data ss:Type=\"String\"></Data></Cell>" f)
        (write-line "    <Cell ss:StyleID=\"BoldUnderline\"><Data ss:Type=\"String\"></Data></Cell>" f)
        (write-line (strcat "    <Cell ss:StyleID=\"BoldUnderlineNum\" ss:Formula=\"=SUM(R" (itoa startRow) "C5:R" (itoa endRow) "C5)\"><Data ss:Type=\"Number\">" (rtos totalSum 2 2) "</Data></Cell>") f)
        (write-line "   </Row>" f)
        (setq rowNum (1+ rowNum))
      )

      (write-line "  </Table>" f)
      (write-line " </Worksheet>" f)
      (write-line "</Workbook>" f)
      (close f)
      T
    )
  )
)

(defun eu-export-subsystem-summary (data xlsfile / f rowNum i name cnt sum totalCount totalSum)
  (setq f (open xlsfile "w"))
  (if (null f)
    nil
    (progn
      (write-line "<?xml version=\"1.0\" encoding=\"windows-1251\"?>" f)
      (write-line "<?mso-application progid=\"Excel.Sheet\"?>" f)
      (write-line "<Workbook xmlns=\"urn:schemas-microsoft-com:office:spreadsheet\"" f)
      (write-line " xmlns:o=\"urn:schemas-microsoft-com:office:office\"" f)
      (write-line " xmlns:x=\"urn:schemas-microsoft-com:office:excel\"" f)
      (write-line " xmlns:ss=\"urn:schemas-microsoft-com:office:spreadsheet\"" f)
      (write-line " xmlns:html=\"http://www.w3.org/TR/REC-html40\">" f)
      (write-line (eu-xml-styles "0.00") f)
      (write-line " <Worksheet ss:Name=\"SubsystemSummary\">" f)
      (write-line "  <Table>" f)
      (write-line "   <Column ss:Width=\"30\"/>" f)
      (write-line "   <Column ss:Width=\"250\"/>" f)
      (write-line "   <Column ss:Width=\"75\"/>" f)
      (write-line "   <Column ss:Width=\"75\"/>" f)
      (write-line "   <Row ss:Height=\"20\">" f)
      (write-line "    <Cell ss:StyleID=\"Header\" ss:MergeAcross=\"3\"><Data ss:Type=\"String\">Подсистема</Data></Cell>" f)
      (write-line "   </Row>" f)
      (write-line "   <Row>" f)
      (write-line "    <Cell ss:StyleID=\"Header\"><Data ss:Type=\"String\">№</Data></Cell>" f)
      (write-line "    <Cell ss:StyleID=\"Header\"><Data ss:Type=\"String\">Наименование</Data></Cell>" f)
      (write-line "    <Cell ss:StyleID=\"Header\"><Data ss:Type=\"String\">Кол-во, шт.</Data></Cell>" f)
      (write-line "    <Cell ss:StyleID=\"Header\"><Data ss:Type=\"String\">Сумма, м.п.</Data></Cell>" f)
      (write-line "   </Row>" f)

      (setq rowNum 3
            i 0)
      (foreach rec data
        (setq i (1+ i)
              name (car rec)
              cnt  (cadr rec)
              sum  (caddr rec))
        (write-line "   <Row>" f)
        (write-line (strcat "    <Cell ss:StyleID=\"Data\"><Data ss:Type=\"Number\">" (itoa i) "</Data></Cell>") f)
        (write-line (strcat "    <Cell ss:StyleID=\"Data\"><Data ss:Type=\"String\">" (eu-xml-escape name) "</Data></Cell>") f)
        (write-line (strcat "    <Cell ss:StyleID=\"Data\"><Data ss:Type=\"Number\">" (itoa cnt) "</Data></Cell>") f)
        (if sum
          (write-line (strcat "    <Cell ss:StyleID=\"Data\"><Data ss:Type=\"Number\">" (rtos sum 2 2) "</Data></Cell>") f)
          (write-line "    <Cell ss:StyleID=\"Data\"><Data ss:Type=\"String\"></Data></Cell>" f)
        )
        (write-line "   </Row>" f)
        (setq rowNum (1+ rowNum))
      )

      (write-line "  </Table>" f)
      (write-line " </Worksheet>" f)
      (write-line "</Workbook>" f)
      (close f)
      T
    )
  )
)

;; CSV для Подсистемы с десятичной запятой
(defun eu-export-subsystem-csv-detail (data csvfile / f rowNum i name len cnt sum totalSum groupName groupRows startRow endRow itemNum)
  (setq f (open csvfile "w"))
  (if f
    (progn
      (write-line "Подсистема" f)
      (write-line "№;Наименование;Длина, мм;Кол-во, шт.;Сумма, м.п." f)
      (setq rowNum 3
            itemNum 0)
      ;; Штучные
      (foreach rec data
        (if (null (cadr rec))
          (progn
            (setq itemNum (1+ itemNum))
            (write-line (strcat (itoa itemNum) ";" (car rec) ";;" (itoa (caddr rec)) ";") f)
          )
        )
      )
      ;; Мерные с подитогами
      (setq groups '())
      (foreach rec data
        (if (cadr rec)
          (if (not (assoc (car rec) groups))
            (setq groups (cons (list (car rec)) groups))
          )
        )
      )
      (setq groups (vl-sort groups '(lambda (a b) (< (car a) (car b)))))
      (foreach grp groups
        (setq groupName (car grp)
              totalSum 0.0)
        (foreach rec data
          (if (and (= (car rec) groupName) (cadr rec))
            (progn
              (setq len (cadr rec)
                    cnt (caddr rec)
                    sum (/ (* len cnt) 1000.0)
                    totalSum (+ totalSum sum))
              (setq itemNum (1+ itemNum))
              (write-line (strcat (itoa itemNum) ";" groupName ";" (rtos len 2 0) ";" (itoa cnt) ";" (vl-string-translate "." "," (rtos sum 2 2))) f)
            )
          )
        )
        ;; Подитог
        (write-line (strcat ";" groupName ";;;" (vl-string-translate "." "," (rtos totalSum 2 2))) f)
      )
      (close f)
      T
    )
    nil
  )
)

(defun eu-export-subsystem-csv-summary (data csvfile / f i name cnt sum)
  (setq f (open csvfile "w"))
  (if f
    (progn
      (write-line "Подсистема" f)
      (write-line "№;Наименование;Кол-во, шт.;Сумма, м.п." f)
      (setq i 0)
      (foreach rec data
        (setq i (1+ i)
              name (car rec)
              cnt  (cadr rec)
              sum  (caddr rec))
        (write-line
          (strcat (itoa i) ";" name ";" (itoa cnt) ";"
                  (if sum (vl-string-translate "." "," (rtos sum 2 2)) "")) f)
      )
      (close f)
      T
    )
    nil
  )
)

;; ============================================================
;; ФУНКЦИИ ДЛЯ ЗАПОЛНЕНИЯ
;; ============================================================

;; ------------------------------------------------------------
;; Округление до двух знаков после запятой (для Заполнения)
;; Применяется ДО суммирования, чтобы подитоги и итоги
;; точно соответствовали сумме отображаемых значений
;; (не терялась 0,01 при накоплении погрешностей).
;; ------------------------------------------------------------
(defun eu-round2 (x)
  (/ (fix (+ (* x 100.0) 0.5)) 100.0)
)

;; ------------------------------------------------------------
;; Форматирование площади для CSV с подавлением лишних нулей
;; 3,00 -> 3 ; 3,10 -> 3,1 ; 3,01 -> 3,01 ; 3,15 -> 3,15
;; ------------------------------------------------------------
(defun eu-format-area-csv (area / int-part frac-hundredths)
  (setq int-part (fix area))
  (setq frac-hundredths (fix (+ (* (- area int-part) 100.0) 0.5)))
  (cond
    ;; Нет дробной части: 3,00 -> 3
    ((= frac-hundredths 0)
     (itoa int-part))
    ;; Сотые нулевые, десятые ненулевые: 3,10 -> 3,1
    ((= (rem frac-hundredths 10) 0)
     (strcat (itoa int-part) "," (itoa (/ frac-hundredths 10))))
    ;; Обе цифры значимые: 3,01 -> 3,01 ; 3,15 -> 3,15
    (T
     (if (< frac-hundredths 10)
       (strcat (itoa int-part) ",0" (itoa frac-hundredths))
       (strcat (itoa int-part) "," (itoa frac-hundredths))
     )
    )
  )
)

;; ------------------------------------------------------------
;; Экспорт Заполнение SUMMARY в XLS (XML Spreadsheet)
;; data: список (тип количество площадь-м2)
;; Формат площади: 0.## (подавление лишних нулей)
;; ------------------------------------------------------------
(defun eu-export-zapolnenie-summary (data xlsfile / f rowNum i rec tip cnt area total-cnt total-area startRow endRow)
  (setq f (open xlsfile "w"))
  (if (null f)
    nil
    (progn
      (write-line "<?xml version=\"1.0\" encoding=\"windows-1251\"?>" f)
      (write-line "<?mso-application progid=\"Excel.Sheet\"?>" f)
      (write-line "<Workbook xmlns=\"urn:schemas-microsoft-com:office:spreadsheet\"" f)
      (write-line " xmlns:o=\"urn:schemas-microsoft-com:office:office\"" f)
      (write-line " xmlns:x=\"urn:schemas-microsoft-com:office:excel\"" f)
      (write-line " xmlns:ss=\"urn:schemas-microsoft-com:office:spreadsheet\"" f)
      (write-line " xmlns:html=\"http://www.w3.org/TR/REC-html40\">" f)
      (write-line (eu-xml-styles "0.##") f)

      (write-line " <Worksheet ss:Name=\"ZapolnenieSummary\">" f)
      (write-line "  <Table>" f)
      (write-line "   <Column ss:Width=\"30\"/>" f)
      (write-line "   <Column ss:Width=\"125\"/>" f)
      (write-line "   <Column ss:Width=\"80\"/>" f)
      (write-line "   <Column ss:Width=\"80\"/>" f)

      (write-line "   <Row ss:Height=\"20\">" f)
      (write-line "    <Cell ss:StyleID=\"Header\" ss:MergeAcross=\"3\"><Data ss:Type=\"String\">Заполнение</Data></Cell>" f)
      (write-line "   </Row>" f)

      (write-line "   <Row>" f)
      (write-line "    <Cell ss:StyleID=\"Header\"><Data ss:Type=\"String\">№</Data></Cell>" f)
      (write-line "    <Cell ss:StyleID=\"Header\"><Data ss:Type=\"String\">Тип</Data></Cell>" f)
      (write-line "    <Cell ss:StyleID=\"Header\"><Data ss:Type=\"String\">Кол-во, шт.</Data></Cell>" f)
      (write-line "    <Cell ss:StyleID=\"Header\"><Data ss:Type=\"String\">Площадь, м2</Data></Cell>" f)
      (write-line "   </Row>" f)

      (setq rowNum 3 i 0 total-cnt 0 total-area 0.0 startRow 3)
      (foreach rec data
        (setq i (1+ i)
              tip (car rec)
              cnt (cadr rec)
              area (caddr rec))
        (setq total-cnt (+ total-cnt cnt)
              total-area (+ total-area area))

        (write-line "   <Row>" f)
        (write-line (strcat "    <Cell ss:StyleID=\"Data\"><Data ss:Type=\"Number\">" (itoa i) "</Data></Cell>") f)
        (write-line (strcat "    <Cell ss:StyleID=\"Data\"><Data ss:Type=\"String\">" (eu-xml-escape tip) "</Data></Cell>") f)
        (write-line (strcat "    <Cell ss:StyleID=\"Data\"><Data ss:Type=\"Number\">" (itoa cnt) "</Data></Cell>") f)
        (write-line (strcat "    <Cell ss:StyleID=\"Num\"><Data ss:Type=\"Number\">" (rtos area 2 2) "</Data></Cell>") f)
        (write-line "   </Row>" f)

        (setq rowNum (1+ rowNum))
      )

      (setq endRow (1- rowNum))

      ;; Итоговая строка с формулами (корректно, т.к. нет промежуточных подитогов)
      (write-line "   <Row>" f)
      (write-line "    <Cell ss:StyleID=\"BoldUnderline\" ss:MergeAcross=\"1\"><Data ss:Type=\"String\">Итого</Data></Cell>" f)
      (write-line (strcat "    <Cell ss:StyleID=\"BoldUnderline\" ss:Formula=\"=SUM(R" (itoa startRow) "C3:R" (itoa endRow) "C3)\"><Data ss:Type=\"Number\">" (itoa total-cnt) "</Data></Cell>") f)
      (write-line (strcat "    <Cell ss:StyleID=\"BoldUnderlineNum\" ss:Formula=\"=SUM(R" (itoa startRow) "C4:R" (itoa endRow) "C4)\"><Data ss:Type=\"Number\">" (rtos total-area 2 2) "</Data></Cell>") f)
      (write-line "   </Row>" f)

      (write-line "  </Table>" f)
      (write-line " </Worksheet>" f)
      (write-line "</Workbook>" f)
      (close f)
      T
    )
  )
)

;; ------------------------------------------------------------
;; Экспорт Заполнение DETAIL в CSV
;; ------------------------------------------------------------
;; Экспорт Заполнение SUMMARY в CSV
;; Разделитель: точка с запятой (единообразно с Подсистемой)
;; Десятичный разделитель: запятая
;; Площадь в кавычках, с подавлением лишних нулей
;; data: список (тип количество площадь-м2)
;; ------------------------------------------------------------
(defun eu-export-zapolnenie-csv-summary (data csvfile / f i rec tip cnt area total-cnt total-area)
  (setq f (open csvfile "w"))
  (if f
    (progn
      (write-line "Заполнение" f)
      (write-line "№;Тип;Кол-во, шт.;Площадь, м2" f)
      (setq i 0 total-cnt 0 total-area 0.0)
      (foreach rec data
        (setq i (1+ i)
              tip (car rec)
              cnt (cadr rec)
              area (caddr rec))
        (setq total-cnt (+ total-cnt cnt)
              total-area (+ total-area area))
        (write-line
          (strcat (itoa i) ";"
                  (eu-csv-quote tip) ";"
                  (itoa cnt) ";"
                  "\"" (eu-format-area-csv area) "\"")
          f)
      )
      ;; Итоговая строка (2 точки с запятой: данные в колонках 3 и 4)
      (write-line
        (strcat "Итого по всем позициям:;;"
                (itoa total-cnt) ";"
                "\"" (eu-format-area-csv total-area) "\"")
        f)
      (close f)
      T
    )
    nil
  )
)



;; ============================================================
;; Этап 4 (U1): примитивы XLS.
;; eu-doc-begin/end, eu-worksheet/end - оболочки документа.
;; eu-column - колонка: ss:Index ставится САМ по курсору (1..N);
;;   задать его руками нельзя - класс дефектов bde9b71 невозможен.
;; eu-row-begin/eu-row-end, eu-cell, eu-cell-skip - писатель строк:
;;   *eu-col* - курсор колонки, тикает сам после каждой ячейки.
;; Значения - всегда строки (числа формировать rtos/itoa до вызова);
;;   текст экранируется eu-xml-escape-ом внутри eu-cell.
;; attrs - доп. атрибуты ячейки строкой (ss:Formula, ss:MergeAcross);
;;   ss:Index через attrs не задавать (контракт шага).
;; ============================================================
(if (null (boundp '*eu-col*)) (setq *eu-col* 1))

(defun eu-doc-begin (f flavor)
  ;; flavor "FULL"  - шапка с xmlns:html (формат CUTLINE/фасонки);
  ;; flavor "BASIC" - компактная шапка, ">" на строке ss (формат CUTSHEET)
  (cond
    ((= flavor "BASIC")
      (write-line "<?xml version=\"1.0\" encoding=\"windows-1251\"?>" f)
      (write-line "<?mso-application progid=\"Excel.Sheet\"?>" f)
      (write-line "<Workbook xmlns=\"urn:schemas-microsoft-com:office:spreadsheet\"" f)
      (write-line " xmlns:o=\"urn:schemas-microsoft-com:office:office\"" f)
      (write-line " xmlns:x=\"urn:schemas-microsoft-com:office:excel\"" f)
      (write-line " xmlns:ss=\"urn:schemas-microsoft-com:office:spreadsheet\">" f))
    (t
      (write-line "<?xml version=\"1.0\" encoding=\"windows-1251\"?>" f)
      (write-line "<?mso-application progid=\"Excel.Sheet\"?>" f)
      (write-line "<Workbook xmlns=\"urn:schemas-microsoft-com:office:spreadsheet\"" f)
      (write-line " xmlns:o=\"urn:schemas-microsoft-com:office:office\"" f)
      (write-line " xmlns:x=\"urn:schemas-microsoft-com:office:excel\"" f)
      (write-line " xmlns:ss=\"urn:schemas-microsoft-com:office:spreadsheet\"" f)
      (write-line " xmlns:html=\"http://www.w3.org/TR/REC-html40\">" f)))
  T)

(defun eu-doc-end (f)
  (write-line "</Workbook>" f)
  T)

(defun eu-worksheet (f name)
  (write-line (strcat " <Worksheet ss:Name=\"" (eu-xml-escape name) "\">") f)
  (write-line "  <Table>" f)
  (setq *eu-col* 1)
  T)

(defun eu-worksheet-end (f)
  (write-line "  </Table>" f)
  (write-line " </Worksheet>" f)
  T)

(defun eu-column (f width autofit)
  ;; width: строка (как есть) или число (rtos 2 1); autofit "0"/"1"
  (write-line (strcat "   <Column ss:Index=\"" (itoa *eu-col*)
                      "\" ss:AutoFitWidth=\"" autofit
                      "\" ss:Width=\"" (if (numberp width) (rtos (float width) 2 1) width)
                      "\"/>") f)
  (setq *eu-col* (1+ *eu-col*))
  T)

(defun eu-row-begin (f attrs / )
  ;; attrs: доп. атрибуты строки строкой ("" = обычная <Row>)
  (setq *eu-col* 1)
  (if (and attrs (/= attrs ""))
    (write-line (strcat "   <Row " attrs ">") f)
    (write-line "   <Row>" f))
  T)

(defun eu-cell (f style type value attrs / )
  (write-line (strcat "    <Cell"
                      (if (/= style "") (strcat " ss:StyleID=\"" style "\"") "")
                      (if (and attrs (/= attrs "")) (strcat " " attrs) "")
                      "><Data ss:Type=\"" type "\">"
                      (eu-xml-escape value)
                      "</Data></Cell>") f)
  (setq *eu-col* (1+ *eu-col*))
  T)

(defun eu-cell-skip (f n / )
  (repeat n
    (write-line "    <Cell/>" f)
    (setq *eu-col* (1+ *eu-col*)))
  T)

(defun eu-row-end (f)
  (write-line "   </Row>" f)
  T)

;; EXCEL-UTILS.LSP загружен.
(princ)
