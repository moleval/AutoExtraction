;;; ============================================================
;;; CUTSHEET.LSP — модуль двумерного раскроя листа
;;; AutoExtraction / AutoCAD 2016+
;;;
;;; РЕДАКЦИЯ 4 (исправления):
;;;   1. Площадь в агрегации — фактическая из записи
;;;   2. Убрано дублирование в диалоге
;;;   3. Вынесена константа *CUTSHEET-MIN-TEXT-AREA*
;;;   4. Уникальные имена блоков
;;;   5. Относительные координаты в summary
;;;   6. Расширены стили XLS
;;;   7. Явная проверка размеров
;;;   8. Динамическая ширина таблицы
;;;   9. Заливка SOLID вместо HATCH (совместимость с cutline)
;;;  10. Таблица: количество деталей напротив типов
;;;  11. Компактная таблица, шкала по низу листа
;;;  12. МаксRects с контактным скорингом
;;; ============================================================

(vl-load-com)

;; ================= ПАРАМЕТРЫ =================
(setq *CUTSHEET-MIN-SIZE*        50.0)
(setq *CUTSHEET-MAX-SIZE*     500000.0)
(setq *CUTSHEET-DEFAULT-WIDTH* 3000.0)
(setq *CUTSHEET-DEFAULT-HEIGHT* 1500.0)
(setq *CUTSHEET-DEFAULT-KERF*   3.0)
(setq *CUTSHEET-DEFAULT-ROTATE* T)

;; Графика
(setq *CUTSHEET-PART-TRANSPARENCY* 0.70)
(setq *CUTSHEET-WASTE-TRANSPARENCY* 0.88)
(setq *CUTSHEET-PALETTE* '(1 2 3 4 5 6 30 210 140 90 40 120))
(setq *CUTSHEET-TITLE-H* 100.0)
(setq *CUTSHEET-TEXT-H*  60.0)
(setq *CUTSHEET-SHEET-GAP* 190.0)   ; видимый вертикальный зазор = GAP+HEADER(260): 450 (требование пользователя)
(setq *CUTSHEET-SHEET-HEADER* 260.0)
(setq *CUTSHEET-GRID-COLS* 3)
(setq *CUTSHEET-SUMMARY-W* 2000.0)
(setq *CUTSHEET-SUMMARY-GAP* 500.0)
(setq *CUTSHEET-OUTLINE-COLOR* 7)
(setq *CUTSHEET-TITLE-COLOR* 5)
(setq *CUTSHEET-HEADER-COLOR* 3)
(setq *CUTSHEET-VALUE-COLOR* 7)
(setq *CUTSHEET-KPD-COLOR* 1)
(setq *CUTSHEET-WASTE-COLOR* 8)
(setq *CUTSHEET-PART-TEXT-COLOR* 2)
;; Марка элемента (атрибут МАРКА динамического блока) в углу детали
(setq *CUTSHEET-MARK-COLOR* 7)
(setq *CUTSHEET-TEXT-COLOR* 7)
(setq *CUTSHEET-FRAME-LAYER* "Невидимые")
(setq *CUTSHEET-FRAME-PAD-LEFT* 200.0)
(setq *CUTSHEET-FRAME-PAD-RIGHT* 200.0)
(setq *CUTSHEET-FRAME-PAD-TOP* 250.0)
(setq *CUTSHEET-FRAME-PAD-BOTTOM* 200.0)
(setq *CUTSHEET-MIN-TEXT-AREA* 50000.0)

;; Этап 2 (V4): именованные SOFT-пределы размеров детали (мм).
;; Аномалии не роняют модуль: объект исключается и попадает в сводку причин.
(setq *CUTSHEET-MIN-PART-DIM* 1.0)
(setq *CUTSHEET-MAX-PART-DIM* 100000.0)

;; Этап 2 (V5): лимит количества деталей - защита от зависания
;; при ошибочной выборке (x100 объектов). Именованный, изменяемый.
;; V5 (уточнение 2026-09-23): превышение = alert (GUI) + GUARD в командную
;; строку + запрос на продолжение; Нет/Enter останавливает (как раньше).
(setq *cs-max-parts* 10000)

;; Этап 2 (V6): страж итераций MaxRects - верхняя граница числа попыток
;; размещения (проверок кандидат-прямоугольников). Именованный, изменяемый.
(setq *cs-max-placement-attempts* 1000000)

;; Эффективный список слоёв раскроя: то, по чему реально собрана выборка
;; (после подстановки слоёв задачи из настроек). Показывается в окне
;; в разделе «Выбранные слои» — как в окне раскроя хлыстов.
(setq *cs-effective-layers* nil)

;; Состояние диалога
(if (not (boundp '*cs-tmp-choice*))    (setq *cs-tmp-choice* 'ALL))
(if (not (boundp '*cs-tmp-sheet-w*))   (setq *cs-tmp-sheet-w* *CUTSHEET-DEFAULT-WIDTH*))
(if (not (boundp '*cs-tmp-sheet-h*))   (setq *cs-tmp-sheet-h* *CUTSHEET-DEFAULT-HEIGHT*))
(if (not (boundp '*cs-tmp-kerf*))      (setq *cs-tmp-kerf* *CUTSHEET-DEFAULT-KERF*))
(if (not (boundp '*cs-tmp-rotate*))    (setq *cs-tmp-rotate* *CUTSHEET-DEFAULT-ROTATE*))
(if (not (boundp '*cs-tmp-xls*))       (setq *cs-tmp-xls* T))
(if (not (boundp '*cs-tmp-acad*))      (setq *cs-tmp-acad* T))
(if (not (boundp '*cs-tmp-dyn-type*))  (setq *cs-tmp-dyn-type* ""))
(if (not (boundp '*cs-dyn-types*))     (setq *cs-dyn-types* '()))
(if (not (boundp '*CUTSHEET-LAST-WIDTH*))  (setq *CUTSHEET-LAST-WIDTH* *CUTSHEET-DEFAULT-WIDTH*))
(if (not (boundp '*CUTSHEET-LAST-HEIGHT*)) (setq *CUTSHEET-LAST-HEIGHT* *CUTSHEET-DEFAULT-HEIGHT*))
(if (not (boundp '*CUTSHEET-LAST-KERF*))   (setq *CUTSHEET-LAST-KERF* *CUTSHEET-DEFAULT-KERF*))
(if (not (boundp '*CUTSHEET-LAST-ROTATE*)) (setq *CUTSHEET-LAST-ROTATE* *CUTSHEET-DEFAULT-ROTATE*))
(if (not (boundp '*CUTSHEET-LAST-XLS*))    (setq *CUTSHEET-LAST-XLS* T))
(if (not (boundp '*CUTSHEET-LAST-ACAD*))   (setq *CUTSHEET-LAST-ACAD* T))

;; ================= СТРОКИ / ЧИСЛА =================
(defun cs-split-string (str delim / pos out item)
  (setq out '())
  (while (setq pos (vl-string-search delim str))
    (setq item (vl-string-trim " \t\r\n" (substr str 1 pos)))
    (if (> (strlen item) 0) (setq out (cons item out)))
    (setq str (substr str (+ pos 2))))
  (setq item (vl-string-trim " \t\r\n" str))
  (if (> (strlen item) 0) (setq out (cons item out)))
  (reverse out))

(defun cs-format-num (x digits)
  (vl-string-translate "." "," (rtos x 2 digits)))

(defun cs-xls-num (x digits)
  (rtos x 2 digits))

(defun cs-itoa-safe (x)
  (itoa (fix (+ x 0.5))))

;; ================= ДИНАМИЧЕСКИЕ БЛОКИ =================
(defun cs-value-to-number (value / x s)
  (cond
    ((numberp value) (float value))
    ((= (type value) 'VARIANT)
     (setq x (vl-catch-all-apply 'vlax-variant-value (list value)))
     (cond
       ((vl-catch-all-error-p x) nil)
       ((numberp x) (float x))
       ((= (type x) 'STR) (cs-value-to-number x))
       (T nil)))
    ((= (type value) 'STR)
     (setq s (vl-string-trim " \t\r\n" value))
     (if (> (strlen s) 0)
       (progn
         (setq s (vl-string-translate "," "." s))
         (while (vl-string-search " " s)
           (setq s (vl-string-subst "" " " s)))
         (setq x (vl-catch-all-apply 'atof (list s)))
         (if (vl-catch-all-error-p x) nil x))
       nil))
    (T nil)))

;; ============================================================
;; БЛОКИ ЗАПОЛНЕНИЯ: размер «в свету» + припуск на раму
;;
;; У таких блоков параметры задают размер ПРОЁМА, а заготовку надо
;; резать больше на припуск. Габарит блока (BoundingBox) для них не
;; годится вовсе: он включает раму и даёт размер в разы больше.
;;
;; Признак блока заполнения — маски блоков задачи ЗАПОЛНЕНИЕ из
;; settings.ini: один список на отчёт и на раскрой, разойтись не могут.
;; Цепочка параметров и припуск — тоже как в ЗАПОЛНЕНИИ.
;; ============================================================

(setq *CUTSHEET-FILL-HEIGHT-KEYS* '("ВЫСОТА В СВЕТУ" "ВЫСОТА"))
(setq *CUTSHEET-FILL-WIDTH-KEYS*  '("ШИРИНА В СВЕТУ" "ШИРИНА" "ДЛИНА"))

;; Сколько блоков обработано как заполнение (для диагностики прогона)
(setq *cs-fill-count* 0)

;; Припуск на раму: настройка задачи ЗАПОЛНЕНИЕ, иначе 26
(defun cs-fill-allowance ( / v)
  (if (= (type ae-settings-frame-allowance) 'SUBR)
    (progn
      (setq v (ae-settings-frame-allowance))
      (if (and (numberp v) (>= v 0)) v 26))
    26)
)

;; Маски блоков заполнения. Пустой список = признак выключен:
;; лучше не применять припуск вовсе, чем применить его ко всему подряд.
(defun cs-fill-masks ( / m)
  (setq m nil)
  (if (= (type ae-settings-task-blocks) 'SUBR)
    (setq m (ae-settings-task-blocks 'ZAPOLNENIE)))
  (if (and m (listp m)) m nil)
)

(defun cs-fill-block-p (ent masks)
  (if (or (null masks) (null ent))
    nil
    (su-block-matches-name-masks-p ent masks))
)

;; Значение параметра: точное совпадение, затем вхождение подстроки.
;; Подстрока нужна для имён вида «Высота в свету, мм».
(defun cs-prop-value-like (props wanted / p)
  (setq p (cs-prop-value props wanted))
  (if p
    p
    (progn
      (foreach x props
        (if (and (null p) (= (type (car x)) 'STR)
                 (vl-string-search (strcase wanted) (strcase (car x))))
          (setq p (cs-value-to-number (cdr x)))))
      (if (numberp p) p nil)))
)

(defun cs-fill-dimension (props keys / v)
  (setq v nil)
  (foreach k keys
    (if (null v) (setq v (cs-prop-value-like props k))))
  (if (and (numberp v) (> v 0.0)) v nil)
)

(defun cs-block-all-props (obj / dyn prop pname pval out)
  (setq out '())
  (setq dyn (vl-catch-all-apply 'vlax-invoke (list obj 'GetDynamicBlockProperties)))
  (if (not (vl-catch-all-error-p dyn))
    (foreach prop dyn
      (setq pname (vl-catch-all-apply 'vla-get-PropertyName (list prop)))
      (if (and (not (vl-catch-all-error-p pname)) (= (type pname) 'STR))
        (progn
          (setq pname (vl-string-trim " \t\r\n" pname))
          (setq pval (vl-catch-all-apply 'vla-get-Value (list prop)))
          (if (not (vl-catch-all-error-p pval))
            (setq out (cons (cons pname pval) out)))))))
  (reverse out))

(defun cs-prop-value (props wanted / p)
  (setq p nil)
  (foreach x props
    (if (and (null p) (= (strcase (car x)) (strcase wanted)))
      (setq p (cdr x))))
  (if p (cs-value-to-number p) nil))

(defun cs-get-effective-name-safe (obj / r)
  (setq r (vl-catch-all-apply 'vla-get-EffectiveName (list obj)))
  (if (vl-catch-all-error-p r)
    (progn
      (setq r (vl-catch-all-apply 'vla-get-Name (list obj)))
      (if (vl-catch-all-error-p r) nil r))
    r))

(defun cs-get-visibility-safe (obj / dyn prop pname val result)
  (setq dyn (vl-catch-all-apply 'vlax-invoke (list obj 'GetDynamicBlockProperties)))
  (if (vl-catch-all-error-p dyn)
    nil
    (progn
      (setq result nil)
      (foreach prop dyn
        (if (null result)
          (progn
            (setq pname (vl-catch-all-apply 'vla-get-PropertyName (list prop)))
            (if (and (not (vl-catch-all-error-p pname))
                     (= (type pname) 'STR)
                     (or (vl-string-search "VISIBILITY" (strcase pname))
                         (vl-string-search "ВИДИМОСТЬ" (strcase pname))))
              (progn
                (setq val (vl-catch-all-apply 'vla-get-Value (list prop)))
                (if (not (vl-catch-all-error-p val))
                  (progn
                    (if (= (type val) 'VARIANT) (setq val (vlax-variant-value val)))
                    (if val (setq result (vl-princ-to-string val))))))))))
      result)))

(defun cs-get-dyn-type-name (ent / obj vis name)
  (setq obj (vl-catch-all-apply 'vlax-ename->vla-object (list ent)))
  (if (vl-catch-all-error-p obj)
    "Без имени"
    (progn
      (setq name (cs-get-effective-name-safe obj))
      (if (and name (= (type name) 'STR) (> (strlen (vl-string-trim " \t\r\n" name)) 0))
        (vl-string-trim " \t\r\n" name)
        (progn
          (setq vis (cs-get-visibility-safe obj))
          (if (and vis (> (strlen (vl-string-trim " \t\r\n" vis)) 0))
            (vl-string-trim " \t\r\n" vis)
            "Без имени"))))))

(defun cs-get-bbox (ent / obj mn mx r p1 p2)
  (setq obj (vl-catch-all-apply 'vlax-ename->vla-object (list ent)))
  (if (vl-catch-all-error-p obj)
    nil
    (progn
      (setq r (vl-catch-all-apply 'vla-GetBoundingBox (list obj 'mn 'mx)))
      (if (vl-catch-all-error-p r)
        nil
        (progn
          (setq p1 (vlax-safearray->list mn) p2 (vlax-safearray->list mx))
          (list p1 p2))))))

(defun cs-bbox-w-h (ent / bb p1 p2)
  (setq bb (cs-get-bbox ent))
  (if bb
    (progn
      (setq p1 (car bb) p2 (cadr bb))
      (list (abs (- (car p2) (car p1))) (abs (- (cadr p2) (cadr p1)))))
    nil))

;; ================= ПОЛИЛИНИИ =================
(defun cs-poly-closed-p (ent / f)
  (setq f (cdr (assoc 70 (entget ent))))
  (if f (= 1 (logand 1 f)) nil))

(defun cs-poly-has-arcs (ent / found)
  (setq found nil)
  (foreach g (entget ent)
    (if (and (= (car g) 42) (> (abs (cdr g)) 1e-8)) (setq found T)))
  found)

(defun cs-poly-area (ent / obj a)
  (setq obj (vl-catch-all-apply 'vlax-ename->vla-object (list ent)))
  (setq a (if (vl-catch-all-error-p obj) nil (vl-catch-all-apply 'vla-get-Area (list obj))))
  (if (and a (not (vl-catch-all-error-p a)) (numberp a) (> a 0.0))
    (/ a 1000000.0)
    0.0))

;; ================= ИСТОЧНИК ОБЪЕКТОВ =================
(defun cs-layer-ok-p (layer layers)
  (if (or (null layers) (= (length layers) 0)) T (su-layer-match-any layer layers)))

(defun cs-build-filter-ss (layers / ss out i ent typ lay masks filtered)
  (if (and (null layers) (= (type ae-settings-task-layers) 'SUBR))
    (setq layers (ae-settings-task-layers 'CUTSHEET)))
  ;; Для раздела «Выбранные слои»: показываем именно то, по чему
  ;; собрана выборка, а не то, что пришло от вызывающего
  (setq *cs-effective-layers* layers)
  (setq ss nil)
  (setq ss (su-take-preselection))
  (if (null ss)
    (setq ss (ssget "_I" '((0 . "LWPOLYLINE,INSERT")))))
  (if (null ss) (setq ss (ssget "_X" '((0 . "LWPOLYLINE,INSERT")))))
  (setq out (ssadd) i 0)
  (if ss
    (repeat (sslength ss)
      (setq ent (ssname ss i)
            typ (cdr (assoc 0 (entget ent)))
            lay (cdr (assoc 8 (entget ent))))
      (if (and (or (= typ "LWPOLYLINE") (= typ "INSERT")) (cs-layer-ok-p lay layers) (not (su-map-entity-p ent)))
        (ssadd ent out))
      (setq i (1+ i))))
  ;; ВНИМАНИЕ: su-filter-ss-by-block-name-masks возвращает nil, если под
  ;; маску не подошёл НИ ОДИН объект. Без этой проверки следующий
  ;; (sslength out) падал с «неверный тип аргумента: lselsetp nil» —
  ;; задача обрывалась вместо понятного сообщения.
  (if (= (type ae-settings-task-blocks) 'SUBR)
    (progn
      (setq masks (ae-settings-task-blocks 'CUTSHEET))
      (setq filtered (su-filter-ss-by-block-name-masks out masks))
      (if (null filtered)
        (progn
          (princ "\n[CUTSHEET][GUARD] Под маску блоков задачи не подошёл ни один объект.")
          (princ "\n  Проверьте Настройки -> Раскрой листа -> Блоки (маски через ;).")
          (setq out nil))
        (setq out filtered))))
  (if (and out (> (sslength out) 0)) out nil))

;; ================= ЗАПИСЬ ЧАСТЕЙ =================
;; ================= ВАЛИДАЦИЯ ГЕОМЕТРИИ (V4) =================
;; *cs-rejects* - assoc-счетчик причин отсева за сбор: (причина . количество).
;; *cs-reject-reason* - причина, выставленная последней попыткой построения записи.

(defun cs-reject-note (reason / cell)
  (if (or (null reason) (= reason "")) (setq reason "причина не зафиксирована"))
  (setq cell (assoc reason *cs-rejects*))
  (if cell
    (setq *cs-rejects* (subst (cons reason (1+ (cdr cell))) cell *cs-rejects*))
    (setq *cs-rejects* (cons (cons reason 1) *cs-rejects*))))

(defun cs-print-rejects ( / cell total)
  (setq total 0)
  (foreach cell *cs-rejects* (setq total (+ total (cdr cell))))
  (if (> total 0)
    (progn
      (princ (strcat "\n[CUTSHEET][VALIDATION] Исключено объектов: " (itoa total)))
      (foreach cell (reverse *cs-rejects*)
        (princ (strcat "\n  " (car cell) ": " (itoa (cdr cell))))))))

(defun cs-poly-record (ent id / ed layer bb wh area arc type nominal)
  ;; V4: отказ всегда с причиной в *cs-reject-reason* - объект не падает в раскрой молча.
  (setq ed (entget ent) layer (cdr (assoc 8 ed)) bb (cs-get-bbox ent)
        *cs-reject-reason* nil)
  (cond
    ((not (cs-poly-closed-p ent))
      (setq *cs-reject-reason* "полилиния не замкнута") nil)
    ((null bb)
      (setq *cs-reject-reason* "нет габаритного контейнера") nil)
    (T
      (setq wh (cs-bbox-w-h ent) area (cs-poly-area ent) arc (cs-poly-has-arcs ent))
      (cond
        ((or (null wh) (not (numberp (car wh))) (not (numberp (cadr wh)))
             (<= (car wh) 0.0) (<= (cadr wh) 0.0))
          (setq *cs-reject-reason* "стороны <= 0 или не числовые") nil)
        ((<= area 0.0)
          (setq *cs-reject-reason* "площадь <= 0") nil)
        ((or (< (car wh) *CUTSHEET-MIN-PART-DIM*) (< (cadr wh) *CUTSHEET-MIN-PART-DIM*))
          (setq *cs-reject-reason* "стороны меньше минимума") nil)
        ((or (> (car wh) *CUTSHEET-MAX-PART-DIM*) (> (cadr wh) *CUTSHEET-MAX-PART-DIM*))
          (setq *cs-reject-reason* "стороны больше максимума") nil)
        (T
          (setq type (if arc "Полилиния (дуги)" "Полилиния"))
          (setq nominal (strcat (cs-itoa-safe (car wh)) "x" (cs-itoa-safe (cadr wh))))
          ;; 11-й элемент — марка (у полилинии её нет), 12-й — тип для отчётов;
          ;; арность записей должна совпадать с блоками
          (list id "POLY" layer type (car wh) (cadr wh) area nominal T ent nil type))))))

(defun cs-block-record (ent id / obj ed layer props typName visName wh w h pW pH
                                 area nominal source fill allow mk)
  ;; V4: отказ всегда с причиной в *cs-reject-reason*.
  (setq ed (entget ent) layer (cdr (assoc 8 ed))
        obj (vl-catch-all-apply 'vlax-ename->vla-object (list ent))
        *cs-reject-reason* nil)
  (cond
    ((vl-catch-all-error-p obj)
      (setq *cs-reject-reason* "ActiveX объекта недоступен") nil)
    (T
      (setq props (cs-block-all-props obj) typName (cs-get-dyn-type-name ent))
      ;; Тип для отчётов - СОСТОЯНИЕ ВИДИМОСТИ блока. cs-get-dyn-type-name
      ;; здесь не годится: он возвращает имя блока, а к видимости обращается
      ;; только когда имени нет. Нет состояния видимости - прочерк, а не имя
      ;; блока и не марка (иначе «Тип» снова совпадёт с «Маркой»).
      (setq visName (cs-get-visibility-safe obj))
      (if (and visName (= (type visName) 'STR))
        (setq visName (vl-string-trim " \t\r\n" visName)))
      (if (or (null visName) (= visName "")) (setq visName "-"))
      (setq fill (cs-fill-block-p ent (cs-fill-masks)))
      (if fill
        ;; ЗАПОЛНЕНИЕ: только «в свету» + припуск. Отката на BoundingBox
        ;; здесь нет намеренно — габарит с рамой дал бы молча неверный
        ;; раскрой, лучше явный отказ с причиной.
        (progn
          (setq allow (cs-fill-allowance))
          (setq pH (cs-fill-dimension props *CUTSHEET-FILL-HEIGHT-KEYS*))
          (setq pW (cs-fill-dimension props *CUTSHEET-FILL-WIDTH-KEYS*))
          (if (and pW pH)
            (progn
              (setq w (float (fix (+ pW allow)))
                    h (float (fix (+ pH allow)))
                    source "Заполнение (в свету + припуск)")
              (setq *cs-fill-count* (1+ *cs-fill-count*))
              ;; имя элемента — марка, если она есть
              (setq mk (tu-entity-mark ent))
              (if mk (setq typName mk)))
            (setq w nil h nil source nil
                  *cs-reject-reason*
                  (if (null pH)
                    "заполнение: не найдена высота (в свету)"
                    "заполнение: не найдена ширина (в свету)"))))
        (progn
          (setq pW (cs-prop-value props "Ширина") pH (cs-prop-value props "Высота"))
          (if (not (numberp pW)) (setq pW nil))
          (if (not (numberp pH)) (setq pH nil))
          (if (and pW pH (> pW 0.0) (> pH 0.0))
            (setq w pW h pH source "Свойства")
            (progn
              (setq wh (cs-bbox-w-h ent))
              (if (and wh (numberp (car wh)) (numberp (cadr wh)) (> (car wh) 0.0) (> (cadr wh) 0.0))
                (setq w (car wh) h (cadr wh) source "BoundingBox")
                (setq w nil h nil source nil))))))
      (cond
        ((or (null w) (null h))
          ;; причина от ветки заполнения точнее — не затираем её
          (if (null *cs-reject-reason*)
            (setq *cs-reject-reason* "размеры не числовые (свойства и BoundingBox)"))
          nil)
        ((or (<= w 0.0) (<= h 0.0))
          (setq *cs-reject-reason* "стороны <= 0") nil)
        ((or (< w *CUTSHEET-MIN-PART-DIM*) (< h *CUTSHEET-MIN-PART-DIM*))
          (setq *cs-reject-reason* "стороны меньше минимума") nil)
        ((or (> w *CUTSHEET-MAX-PART-DIM*) (> h *CUTSHEET-MAX-PART-DIM*))
          (setq *cs-reject-reason* "стороны больше максимума") nil)
        (T
          (setq area (/ (* w h) 1000000.0))
          (setq nominal (strcat (cs-itoa-safe w) "x" (cs-itoa-safe h)))
          ;; 11-й элемент — марка из атрибута блока (nil, если нет),
          ;; 12-й — тип для отчётов: видимость блока без подмены маркой
          (list id "DYN" layer typName w h area nominal source ent
                (tu-entity-mark ent) visName))))))

(defun cs-collect-records (ss choice dynType / i ent typ rec out id)
  (setq out '() i 0 id 0 *cs-rejects* '() *cs-fill-count* 0)
  (if ss
    (repeat (sslength ss)
      (setq ent (ssname ss i) typ (cdr (assoc 0 (entget ent))) rec nil)
      (cond
        ((and (= typ "LWPOLYLINE") (or (eq choice 'ALL) (eq choice 'POLY)))
         (setq id (1+ id))
         (setq rec (cs-poly-record ent id))
         (if (null rec) (cs-reject-note *cs-reject-reason*)))
        ((and (= typ "INSERT") (or (eq choice 'ALL) (eq choice 'DYN)))
         (cond
           ((eq choice 'ALL)
            (setq id (1+ id))
            (setq rec (cs-block-record ent id))
            (if (null rec) (cs-reject-note *cs-reject-reason*)))
           ((or (null dynType) (= dynType "") (= dynType "Все типы блоков"))
            (setq id (1+ id))
            (setq rec (cs-block-record ent id))
            (if (null rec) (cs-reject-note *cs-reject-reason*)))
           ((= (cs-get-dyn-type-name ent) dynType)
            (setq id (1+ id))
            (setq rec (cs-block-record ent id))
            (if (null rec) (cs-reject-note *cs-reject-reason*))))))
      (if rec (setq out (cons rec out)))
      (setq i (1+ i))))
  (reverse out))

(defun cs-collect-dyn-types (ss / i ent typ nm out)
  (setq i 0 out '())
  (if ss
    (repeat (sslength ss)
      (setq ent (ssname ss i) typ (cdr (assoc 0 (entget ent))))
      (if (= typ "INSERT")
        (progn
          (setq nm (cs-get-dyn-type-name ent))
          (if (and nm (not (member nm out))) (setq out (cons nm out)))))
      (setq i (1+ i))))
  (vl-sort out '(lambda (a b) (< (strcase a) (strcase b)))))

(defun cs-count-type (ss kind / i ent typ obj cnt wh)
  (setq i 0 cnt 0)
  (if ss
    (repeat (sslength ss)
      (setq ent (ssname ss i) typ (cdr (assoc 0 (entget ent))))
      (cond
        ((and (eq kind 'POLY) (= typ "LWPOLYLINE"))
         (if (cs-poly-closed-p ent) (setq cnt (1+ cnt))))
        ((and (eq kind 'DYN) (= typ "INSERT"))
         (setq obj (vl-catch-all-apply 'vlax-ename->vla-object (list ent)))
         (if (not (vl-catch-all-error-p obj))
           (progn
             (setq wh (cs-bbox-w-h ent))
             (if (and wh (> (car wh) 0.0) (> (cadr wh) 0.0)) (setq cnt (1+ cnt))))))
        ((eq kind 'ALL)
         (if (or (= typ "LWPOLYLINE") (= typ "INSERT")) (setq cnt (1+ cnt)))))
      (setq i (1+ i))))
  cnt)

;; ============================================================
;; Отображение списка слоёв (зеркало CUTLINE: n1-layer-display-list)
;; Слои выбирает диспетчер; окно раскроя только показывает их.
;; ============================================================

;; «по фильтру: Мои» / «по фильтрам: Фасады, Окна» либо nil.
;; Непусто только когда слои пришли от групповых фильтров.
(defun cs-filter-name-str ( / s)
  (setq s nil)
  (if (= (type extraction-layer-filter-source-title) 'SUBR)
    (setq s (extraction-layer-filter-source-title))
  )
  s
)

(defun cs-layer-display-list (layers / fname)
  (setq fname (cs-filter-name-str))
  (cond
    ((and fname (= (type fname) 'STR) (/= fname ""))
     (list (strcat fname " (за исключением слоя 0)"))
    )
    ((or (null layers) (not (listp layers)) (= (length layers) 0))
     (list "Все слои")
    )
    (T layers)
  )
)


;; «Фильтр Витражи» / «Фильтры Фасады, Окна» либо nil
(defun cs-filter-header-str ( / keys s)
  (setq s nil)
  (if (and (cs-filter-name-str)
           (= (type extraction-layer-filter-list-str) 'SUBR)
           (boundp '*EXTRACTION-LAYER-FILTERS*))
    (progn
      (setq keys *EXTRACTION-LAYER-FILTERS*)
      (setq s (extraction-layer-filter-list-str keys))
      (setq s
        (if (= s "")
          nil
          (strcat (if (= (length keys) 1) "Фильтр " "Фильтры ") s)))
    )
  )
  s
)

;; Заголовок рамки: «Выбранные слои (Фильтр Витражи: 31 слой)»
;; либо «Выбранные слои (3 слоя)» / «Выбранные слои (все слои)»
(defun cs-layers-header-text (layers / n f)
  (setq n (if (listp layers) (length layers) 0))
  (setq f (cs-filter-header-str))
  (cond
    (f (strcat "Выбранные слои (" f ": " (itoa n) " " (tu-layer-word n) ")"))
    ((<= n 0) "Выбранные слои (все слои)")
    (T (strcat "Выбранные слои (" (itoa n) " " (tu-layer-word n) ")"))
  )
)

;; ================= DCL =================
(defun cs-safe-set-tile (key val) (vl-catch-all-apply 'set_tile (list key val)))
(defun cs-safe-mode-tile (key mode) (vl-catch-all-apply 'mode_tile (list key mode)))

;; Этап 2 (V7): помещается ли деталь на лист хотя бы в одной из
;; допустимых ориентаций (рез учитывает солвер; здесь - геометрия).
(defun cs-part-fits-sheet-p (w h sheetW sheetH rotateFlag)
  (or (and (<= w sheetW) (<= h sheetH))
      (and rotateFlag (<= h sheetW) (<= w sheetH))))

(defun cs-cut-sizes-valid-p (w h kerf)
  (and (numberp w) (numberp h) (> w *CUTSHEET-MIN-SIZE*) (> h *CUTSHEET-MIN-SIZE*)
       (< w *CUTSHEET-MAX-SIZE*) (< h *CUTSHEET-MAX-SIZE*)
       (numberp kerf) (>= kerf 0.0) (< kerf (min w h))))

;; ============================================================
;; Ручное управление радиокнопками (аналог n1-select-radio из cutline.lsp)
;; ============================================================
(defun cs-select-radio (selected / keys k)
  (setq keys '("rb_all" "rb_poly" "rb_dyn"))
  (foreach k keys
    (cs-safe-set-tile k (if (= k selected) "1" "0"))
  )
  (cond
    ((= selected "rb_all")  (setq *cs-tmp-choice* 'ALL)  (cs-safe-mode-tile "popup_dyn_type" 1))
    ((= selected "rb_poly") (setq *cs-tmp-choice* 'POLY) (cs-safe-mode-tile "popup_dyn_type" 1))
    ((= selected "rb_dyn")  (setq *cs-tmp-choice* 'DYN)  (cs-safe-mode-tile "popup_dyn_type" 0))
  )
)

(defun cs-dialog (polyCnt dynCnt dynTypes ss defaultW defaultH defaultKerf defaultRotate defaultXls defaultAcad / dcl-file dcl-id result dcl-src)
  (setq dcl-src (findfile "cutsheet_filter.dcl"))
  ;; Заголовок рамки «Выбранные слои» статичен в DCL — подменяется
  ;; во временной копии файла; при неудаче берётся исходный файл
  (setq dcl-file
    (if dcl-src
      (tu-dcl-with-label dcl-src "label = \"Выбранные слои"
        (cs-layers-header-text *cs-effective-layers*))
      nil))
  (if (null dcl-file)
    (progn (princ "\n[CUTSHEET] Не найден cutsheet_filter.dcl.") nil)
    (progn
      (setq dcl-id (load_dialog dcl-file))
      (if (< dcl-id 0)
        (progn (princ "\n[CUTSHEET] Ошибка load_dialog.")
               (tu-dcl-cleanup dcl-file dcl-src) nil)
        (progn
          (setq *cs-tmp-choice* 'ALL
                *cs-tmp-sheet-w* defaultW
                *cs-tmp-sheet-h* defaultH
                *cs-tmp-kerf* defaultKerf
                *cs-tmp-rotate* defaultRotate
                *cs-tmp-xls* defaultXls
                *cs-tmp-acad* defaultAcad
                *cs-tmp-dyn-type* "")
          (if (not (new_dialog "cutsheet_filter_dialog" dcl-id))
            (progn (vl-catch-all-apply 'unload_dialog (list dcl-id))
                   (tu-dcl-cleanup dcl-file dcl-src) nil)
            (progn
              (cs-safe-set-tile "txt_poly_count" (strcat (itoa polyCnt) " шт."))
              (cs-safe-set-tile "txt_dyn_count" (strcat (itoa dynCnt) " шт."))
              (cs-safe-set-tile "txt_all_count" (strcat (itoa (+ polyCnt dynCnt)) " шт."))
              (setq *cs-dyn-types* dynTypes)
              (start_list "popup_dyn_type")
              (add_list "Все типы блоков")
              (foreach x dynTypes (add_list x))
              (end_list)
              (set_tile "popup_dyn_type" "0")
              (cs-safe-mode-tile "popup_dyn_type" 1)

              ;; «Выбранные слои»: только информация. Заполнение под
              ;; перехватом — диагностика не должна ронять диалог.
              (vl-catch-all-apply
                '(lambda ()
                   (start_list "lst_layers")
                   (foreach l (cs-layer-display-list *cs-effective-layers*)
                     (add_list l))
                   (end_list))
                nil)

              (if (<= polyCnt 0) (cs-safe-mode-tile "rb_poly" 1))
              (if (<= dynCnt 0) (cs-safe-mode-tile "rb_dyn" 1))
              (if (<= (+ polyCnt dynCnt) 0) (cs-safe-mode-tile "rb_all" 1))
              (cs-safe-set-tile "rb_all" "1")
              (cs-safe-set-tile "rb_poly" "0")
              (cs-safe-set-tile "rb_dyn" "0")
              (cs-safe-set-tile "edt_sheet_w" (rtos defaultW 2 0))
              (cs-safe-set-tile "edt_sheet_h" (rtos defaultH 2 0))
              (cs-safe-set-tile "edt_kerf" (rtos defaultKerf 2 2))
              (cs-safe-set-tile "chk_rotate" (if defaultRotate "1" "0"))
              (cs-safe-set-tile "chk_xls" (if defaultXls "1" "0"))
              (cs-safe-set-tile "chk_acad" (if defaultAcad "1" "0"))
              (action_tile "rb_all"  "(cs-select-radio \"rb_all\")")
              (action_tile "rb_poly" "(cs-select-radio \"rb_poly\")")
              (action_tile "rb_dyn"  "(cs-select-radio \"rb_dyn\")")
              (action_tile "popup_dyn_type"
                "(if (= (atoi $value) 0) (setq *cs-tmp-dyn-type* \"\") (setq *cs-tmp-dyn-type* (nth (1- (atoi $value)) *cs-dyn-types*))) (setq *cs-tmp-choice* 'DYN) (mode_tile \"popup_dyn_type\" 0)")
              (action_tile "edt_sheet_w" "(setq *cs-tmp-sheet-w* (tu-parse-number $value))")
              (action_tile "edt_sheet_h" "(setq *cs-tmp-sheet-h* (tu-parse-number $value))")
              (action_tile "edt_kerf"    "(setq *cs-tmp-kerf* (tu-parse-number $value))")
              (action_tile "chk_rotate" "(setq *cs-tmp-rotate* (= $value \"1\"))")
              (action_tile "chk_xls"    "(setq *cs-tmp-xls* (= $value \"1\"))")
              (action_tile "chk_acad"   "(setq *cs-tmp-acad* (= $value \"1\"))")
              (action_tile "btn_ok"     "(if (cs-cut-sizes-valid-p *cs-tmp-sheet-w* *cs-tmp-sheet-h* *cs-tmp-kerf*) (done_dialog 1) (alert \"[AutoExtraction][CUTSHEET][VALIDATION] Проверьте размеры листа и ширину реза (рез неотрицательный и меньше сторон листа).\"))")
              (action_tile "btn_cancel" "(done_dialog 0)")
              (setq result (start_dialog))
              (vl-catch-all-apply 'unload_dialog (list dcl-id))
              (tu-dcl-cleanup dcl-file dcl-src)
              (if (= result 1)
                (list *cs-tmp-choice* *cs-tmp-sheet-w* *cs-tmp-sheet-h* *cs-tmp-kerf*
                      *cs-tmp-rotate* *cs-tmp-xls* *cs-tmp-acad* *cs-tmp-dyn-type*)
                nil))))))))

;; ================= АГРЕГАЦИЯ =================
(defun cs-part-key (r)
  (strcat (nth 1 r) "|" (nth 3 r) "|" (cs-itoa-safe (nth 4 r)) "x" (cs-itoa-safe (nth 5 r))))

(defun cs-part-label (r)
  (strcat (cs-itoa-safe (nth 4 r)) "x" (cs-itoa-safe (nth 5 r))))

;; Марка детали либо nil. Длина записи проверяется: старые записи короче.
(defun cs-part-mark (r / v)
  (setq v (if (and (listp r) (> (length r) 10)) (nth 10 r) nil))
  (if (and v (= (type v) 'STR) (/= v "")) v nil))

;; Тип для отчётов — состояние видимости блока. В (nth 3) у блоков ЗАПОЛНЕНИЯ
;; марка: cs-block-record подменяет тип маркой, и без отдельного поля колонки
;; «Тип» и «Марка» в XLS и CSV печатали одно и то же.
(defun cs-part-type (r)
  (if (and (listp r) (> (length r) 11) (nth 11 r)) (nth 11 r) (nth 3 r)))

;; То же для записи группы: тип для отчётов лежит 11-м элементом (cs-aggregate).
(defun cs-group-type (g)
  (if (and (listp g) (> (length g) 10) (nth 10 g)) (nth 10 g) (nth 3 g)))

;; Количество по каждой марке внутри группы: (марка . количество).
;; Раньше хранился только список марок без количеств, и в сводке
;; печаталось «первая +N» — это читалось как часть названия марки.
(defun cs-marks-add (lst mk / f)
  (if (null mk)
    lst
    (progn
      (setq f (assoc mk lst))
      (if f
        (subst (cons mk (1+ (cdr f))) f lst)
        (append lst (list (cons mk 1))))))
)

;; Есть ли хотя бы одна марка среди деталей прогона (размещённые и
;; неразмещённые). Колонка «Марка» в XLS/CSV появляется только тогда:
;; без марок состав файлов остаётся прежним, как и в таблице AutoCAD.
(defun cs-xls-has-marks (sheets oversized / has sh p)
  (setq has nil)
  (foreach sh sheets
    (foreach p (cadr sh)
      (if (cs-part-mark (car p)) (setq has T))))
  (foreach p oversized
    (if (cs-part-mark p) (setq has T)))
  (if has T nil)
)

(defun cs-aggregate (records / acc r key f out mk)
  (setq acc '())
  (foreach r records
    (setq key (cs-part-key r) f (assoc key acc))
    (setq mk (cs-part-mark r))
    (if f
      (setq acc (subst (list key (nth 1 r) (nth 2 r) (nth 3 r) (nth 4 r) (nth 5 r)
                             (1+ (nth 6 f)) (+ (nth 7 f) (* (nth 4 r) (nth 5 r) (/ 1.0 1000000.0))) (+ (nth 8 f) (nth 6 r))
                             ;; 10-й элемент — (марка . количество) по группе
                             (cs-marks-add (nth 9 f) mk)
                             ;; 11-й элемент — тип для отчётов (видимость)
                             (cs-part-type r)) f acc))
      (setq acc (cons (list key (nth 1 r) (nth 2 r) (nth 3 r) (nth 4 r) (nth 5 r) 1
                            (* (nth 4 r) (nth 5 r) (/ 1.0 1000000.0)) (nth 6 r)
                            (cs-marks-add '() mk) (cs-part-type r)) acc))))
  (setq out (vl-sort acc '(lambda (a b)
    (cond
      ((> (* (nth 4 a) (nth 5 a)) (* (nth 4 b) (nth 5 b))) T)
      ((< (* (nth 4 a) (nth 5 a)) (* (nth 4 b) (nth 5 b))) nil)
      ((< (strcase (nth 3 a)) (strcase (nth 3 b))) T)
      ((> (strcase (nth 3 a)) (strcase (nth 3 b))) nil)
      (T nil)))))
  out)

;; ================= SORT / NESTING (MaxRects с контактным скорингом) =================
(defun cs-merge-eps () 0.001)

;; Скоринг размещения с контактами и прижимом к началу
(defun cs-score-rect (rw rh fx fy fw fh usedParts curSheet sheetW sheetH / areaFit shortFit longFit fragmentation contact alignBonus distPenalty score p px py pw ph overlap)
  (setq areaFit (- (* fw fh) (* rw rh)))
  (setq shortFit (if (< (- fw rw) (- fh rh)) (- fw rw) (- fh rh)))
  (setq longFit (if (> (- fw rw) (- fh rh)) (- fw rw) (- fh rh)))
  (setq fragmentation (abs (- (- fw rw) (- fh rh))))
  
  (setq contact 0.0)
  (if (<= fx (cs-merge-eps)) (setq contact (+ contact (* rh 15.0))))
  (if (<= fy (cs-merge-eps)) (setq contact (+ contact (* rw 15.0))))
  (if (>= (+ fx rw) (- sheetW (cs-merge-eps))) (setq contact (+ contact (* rh 15.0))))
  (if (>= (+ fy rh) (- sheetH (cs-merge-eps))) (setq contact (+ contact (* rw 15.0))))
  (if (< (- fw rw) (cs-merge-eps)) (setq contact (+ contact (* rh 5.0))))
  (if (< (- fh rh) (cs-merge-eps)) (setq contact (+ contact (* rw 5.0))))
  
  (setq alignBonus 0.0)
  (foreach p usedParts
    (if (= (car p) curSheet)
      (progn
        (setq px (nth 1 p) py (nth 2 p) pw (nth 3 p) ph (nth 4 p))
        (if (or (< (abs (- px (+ fx rw))) (cs-merge-eps))
                (< (abs (- (+ px pw) fx)) (cs-merge-eps)))
          (progn
            (setq overlap (- (min (+ py ph) (+ fy rh)) (max py fy)))
            (if (> overlap 0) (setq contact (+ contact (* overlap 20.0))))))
        (if (or (< (abs (- py (+ fy rh))) (cs-merge-eps))
                (< (abs (- (+ py ph) fy)) (cs-merge-eps)))
          (progn
            (setq overlap (- (min (+ px pw) (+ fx rw)) (max px fx)))
            (if (> overlap 0) (setq contact (+ contact (* overlap 20.0))))))
        (if (< (abs (- fx px)) (cs-merge-eps)) (setq alignBonus (+ alignBonus 80.0)))
        (if (< (abs (- fy py)) (cs-merge-eps)) (setq alignBonus (+ alignBonus 80.0)))
        (if (< (abs (- (+ fx rw) (+ px pw))) (cs-merge-eps)) (setq alignBonus (+ alignBonus 50.0)))
        (if (< (abs (- (+ fy rh) (+ py ph))) (cs-merge-eps)) (setq alignBonus (+ alignBonus 50.0))))))
  
  (setq distPenalty (+ (* fx 0.3) (* fy 0.3)))
  (setq score (+ (* areaFit 0.001) (* shortFit 5.0) (* longFit 1.0) (* fragmentation 0.5)
                 (- (* contact 12.0)) (- alignBonus) distPenalty))
  score)

(defun cs-subtract-rect (freeRects rx ry rw rh kerf / newFree fr fx fy fw fh)
  (setq newFree '())
  (foreach fr freeRects
    (setq fx (nth 0 fr) fy (nth 1 fr) fw (nth 2 fr) fh (nth 3 fr))
    (if (or (>= rx (+ fx fw)) (<= (+ rx rw) fx) (>= ry (+ fy fh)) (<= (+ ry rh) fy))
      (setq newFree (cons fr newFree))
      (progn
        (if (> (- ry fy) kerf) (setq newFree (cons (list fx fy fw (- ry fy kerf)) newFree)))
        (if (> (- (+ fy fh) (+ ry rh)) kerf) (setq newFree (cons (list fx (+ ry rh kerf) fw (- (+ fy fh) (+ ry rh) kerf)) newFree)))
        (if (> (- rx fx) kerf) (setq newFree (cons (list fx fy (- rx fx kerf) fh) newFree)))
        (if (> (- (+ fx fw) (+ rx rw)) kerf) (setq newFree (cons (list (+ rx rw kerf) fy (- (+ fx fw) (+ rx rw) kerf) fh) newFree))))))
  (cs-prune-free-small newFree))

(defun cs-prune-free-small (freeRects / out fr)
  (setq out '())
  (foreach fr freeRects
    (if (and (> (nth 2 fr) 1.0) (> (nth 3 fr) 1.0)) (setq out (cons fr out))))
  (reverse out))

(defun cs-get-used-parts (sheet / out p)
  (setq out '())
  (foreach p (cadr sheet)
    (setq out (cons (list 0 (nth 1 p) (nth 2 p) (nth 3 p) (nth 4 p)) out)))
  (reverse out))

(defun cs-pack-rects (parts sheetW sheetH kerf rotateFlag / sheets oversized freeRects part pw ph bestScore bestX bestY bestW bestH bestRot bestSheetIdx found fr fx fy fw fh score sheetIdx sheet attempts stopGuard)
  ;; V6: страж итераций - считает попытки размещения; при превышении лимита
  ;; остаток деталей уходит в неразмещенные (честный частичный результат).
  (setq sheets '() oversized '() attempts 0 stopGuard nil)
  (setq sheets (list (list (list (list 0.0 0.0 sheetW sheetH)) '() 0.0 0.0)))
  
  (foreach part parts
    (if stopGuard
      (setq oversized (cons part oversized))
      (progn
    (setq pw (nth 4 part) ph (nth 5 part))
    (setq bestScore 1e15 bestX nil bestY nil bestW nil bestH nil bestRot 0 bestSheetIdx nil found nil)
    (setq sheetIdx 0)

    (foreach sheet sheets
      (setq freeRects (car sheet))
      (foreach fr freeRects
        (if (not stopGuard)
          (progn
            (setq attempts (1+ attempts))
            (if (>= attempts *cs-max-placement-attempts*)
              (setq stopGuard T)
              (progn
        (setq fx (nth 0 fr) fy (nth 1 fr) fw (nth 2 fr) fh (nth 3 fr))
        (if (and (<= pw fw) (<= ph fh))
          (progn
            (setq score (cs-score-rect pw ph fx fy fw fh (cs-get-used-parts sheet) sheetIdx sheetW sheetH))
            (if (< score bestScore)
              (setq bestScore score bestX fx bestY fy bestW pw bestH ph bestRot 0 bestSheetIdx sheetIdx found T))))
        (if (and rotateFlag (<= ph fw) (<= pw fh))
          (progn
            (setq score (cs-score-rect ph pw fx fy fw fh (cs-get-used-parts sheet) sheetIdx sheetW sheetH))
            (if (< score bestScore)
              (setq bestScore score bestX fx bestY fy bestW ph bestH pw bestRot 1 bestSheetIdx sheetIdx found T)))))))))
      (setq sheetIdx (1+ sheetIdx)))

    (if (and (not found) (not stopGuard))
      (progn
        (setq sheets (append sheets (list (list (list (list 0.0 0.0 sheetW sheetH)) '() 0.0 0.0))))
        (setq sheetIdx (1- (length sheets)))
        (setq freeRects (list (list 0.0 0.0 sheetW sheetH)))
        (foreach fr freeRects
          (setq fx (nth 0 fr) fy (nth 1 fr) fw (nth 2 fr) fh (nth 3 fr))
          (if (and (<= pw fw) (<= ph fh))
            (progn
              (setq score (cs-score-rect pw ph fx fy fw fh '() sheetIdx sheetW sheetH))
              (if (< score bestScore)
                (setq bestScore score bestX fx bestY fy bestW pw bestH ph bestRot 0 bestSheetIdx sheetIdx found T))))
          (if (and rotateFlag (<= ph fw) (<= pw fh))
            (progn
              (setq score (cs-score-rect ph pw fx fy fw fh '() sheetIdx sheetW sheetH))
              (if (< score bestScore)
                (setq bestScore score bestX fx bestY fy bestW ph bestH pw bestRot 1 bestSheetIdx sheetIdx found T)))))))
    
    (if found
      (progn
        (setq sheet (nth bestSheetIdx sheets))
        (setq sheet (list
                      (cs-subtract-rect (car sheet) bestX bestY bestW bestH kerf)
                      (cons (list part bestX bestY bestW bestH bestRot) (cadr sheet))
                      (+ (nth 2 sheet) (* bestW bestH (/ 1.0 1000000.0)))
                      (+ (nth 3 sheet) (nth 6 part))))
        (setq sheets (subst sheet (nth bestSheetIdx sheets) sheets)))
      (setq oversized (cons part oversized))))))
  (if stopGuard
    (princ (strcat "\n[CUTSHEET][GUARD] Алгоритм остановлен ограничителем попыток ("
                    (itoa *cs-max-placement-attempts*) "). Размещено: "
                    (itoa (- (length parts) (length oversized))) "/"
                    (itoa (length parts)))))
  (list sheets (reverse oversized)))

(defun cs-sort-by-area (records)
  (vl-sort records '(lambda (a b) (> (* (nth 4 a) (nth 5 a)) (* (nth 4 b) (nth 5 b))))))

(defun cs-sort-by-max-side (records)
  (vl-sort records '(lambda (a b) (> (max (nth 4 a) (nth 5 a)) (max (nth 4 b) (nth 5 b))))))

(defun cs-sort-by-min-side (records)
  (vl-sort records '(lambda (a b) (> (min (nth 4 a) (nth 5 a)) (min (nth 4 b) (nth 5 b))))))

(defun cs-calc-utilization (sheets sheetW sheetH / used)
  (setq used 0.0)
  (foreach sheet sheets (setq used (+ used (nth 2 sheet))))
  (if (> (length sheets) 0)
    (/ (* used 100.0) (* (length sheets) sheetW sheetH (/ 1.0 1000000.0)))
    0.0))

(defun cs-nest (parts sheetW sheetH kerf rotateFlag / result1 result2 result3 bestResult bestSheets bestUtil sheets util)
  (grtext -1 "CUTSHEET: раскладка, эвристика 1/3 (площадь)...")
  (pu-begin "CUTSHEET:pack:area")
  (setq result1 (cs-pack-rects (cs-sort-by-area parts) sheetW sheetH kerf rotateFlag))
  (pu-end "CUTSHEET:pack:area")
  (setq sheets (car result1) util (cs-calc-utilization sheets sheetW sheetH))
  (setq bestResult result1 bestSheets (length sheets) bestUtil util)
  
  (grtext -1 "CUTSHEET: раскладка, эвристика 2/3 (макс. сторона)...")
  (pu-begin "CUTSHEET:pack:max-side")
  (setq result2 (cs-pack-rects (cs-sort-by-max-side parts) sheetW sheetH kerf rotateFlag))
  (pu-end "CUTSHEET:pack:max-side")
  (setq sheets (car result2) util (cs-calc-utilization sheets sheetW sheetH))
  (if (or (< (length sheets) bestSheets) (and (= (length sheets) bestSheets) (> util bestUtil)))
    (setq bestResult result2 bestSheets (length sheets) bestUtil util))
  
  (grtext -1 "CUTSHEET: раскладка, эвристика 3/3 (мин. сторона)...")
  (pu-begin "CUTSHEET:pack:min-side")
  (setq result3 (cs-pack-rects (cs-sort-by-min-side parts) sheetW sheetH kerf rotateFlag))
  (pu-end "CUTSHEET:pack:min-side")
  (setq sheets (car result3) util (cs-calc-utilization sheets sheetW sheetH))
  (if (or (< (length sheets) bestSheets) (and (= (length sheets) bestSheets) (> util bestUtil)))
    (setq bestResult result3 bestSheets (length sheets) bestUtil util))
  
  (grtext -1 "CUTSHEET: оптимизация последнего листа...")
  (setq bestResult (list (cs-optimize-last-sheet (car bestResult) sheetW sheetH kerf rotateFlag) (cadr bestResult)))
  bestResult)

(defun cs-optimize-last-sheet (sheets sheetW sheetH kerf rotateFlag / lastSheet lastParts result1 result2 result3 bestResult bestScore score newSheets)
  (if (or (null sheets) (<= (length sheets) 1))
    sheets
    (progn
      (setq lastSheet (last sheets))
      (if (or (null lastSheet) (not (listp lastSheet)))
        sheets
        (progn
          (setq lastParts (mapcar '(lambda (p) (car p)) (cadr lastSheet)))
          (if (or (null lastParts) (<= (length lastParts) 1))
            sheets
            (progn
              (pu-begin "CUTSHEET:pack:lastsheet:area")
              (setq result1 (cs-pack-rects (cs-sort-by-area lastParts) sheetW sheetH kerf rotateFlag))
              (pu-end "CUTSHEET:pack:lastsheet:area")
              (setq bestResult result1 bestScore (cs-calc-utilization (car result1) sheetW sheetH))
              (pu-begin "CUTSHEET:pack:lastsheet:area-rev")
              (setq result2 (cs-pack-rects (reverse (cs-sort-by-area lastParts)) sheetW sheetH kerf rotateFlag))
              (pu-end "CUTSHEET:pack:lastsheet:area-rev")
              (setq score (cs-calc-utilization (car result2) sheetW sheetH))
              (if (> score bestScore) (setq bestResult result2 bestScore score))
              (pu-begin "CUTSHEET:pack:lastsheet:min-side")
              (setq result3 (cs-pack-rects (cs-sort-by-min-side lastParts) sheetW sheetH kerf rotateFlag))
              (pu-end "CUTSHEET:pack:lastsheet:min-side")
              (setq score (cs-calc-utilization (car result3) sheetW sheetH))
              (if (> score bestScore) (setq bestResult result3 bestScore score))
              (setq newSheets (append (reverse (cdr (reverse sheets))) (car bestResult)))
              newSheets)))))))

;; ================= СТАТИСТИКА =================
(defun cs-total-actual-area-records (records / a r) (setq a 0.0) (foreach r records (setq a (+ a (nth 6 r)))) a)
(defun cs-total-bbox-area-records (records / a r) (setq a 0.0) (foreach r records (setq a (+ a (* (nth 4 r) (nth 5 r) (/ 1.0 1000000.0))))) a)

;; ============================================================
;; УЧЁТ ОБЪЕКТОВ КАРТЫ (ред. 25)
;; Набор для упаковки в блок — ТОЛЬКО объекты, созданные отрисовкой.
;; Обход базы (entnext) для этого не годится: он затягивает посторонние
;; объекты чертежа (ATTRIB/SEQEND динамических блоков), CopyObjects на таком
;; составе падает с «Недопустимый объект-владелец», а оригиналы деталей
;; могли быть удалены как «оригиналы карты».
;; ============================================================

(if (not (boundp '*cs-created*))
  (setq *cs-created* nil)
)
(if (not (boundp '*cs-created-miss*))
  (setq *cs-created-miss* 0)
)

;; Всё, что печатается, приводится к строке: диагностика не имеет права
;; упасть на чужом типе значения (например, на имени объекта вместо строки).
(defun cs-safe-str (x)
  (if (= (type x) 'STR) x (vl-princ-to-string x))
)

(defun cs-type-key (typ / s)
  (setq s (cs-safe-str typ))
  (strcase s)
)

;; Создать объект и запомнить его в *cs-created*.
;; Тип проверяется: entlast обязан вернуть именно созданный объект.
(defun cs-mk (dxf / want before res e)
  (setq want (cs-type-key (cdr (assoc 0 dxf))))
  (setq before (entlast))
  (setq res (entmake dxf))
  (if res
    (progn
      (setq e (entlast))
      (if (and e (not (eq e before))
               (= (cs-type-key (cdr (assoc 0 (entget e)))) want))
        (setq *cs-created* (cons e *cs-created*))
        (setq *cs-created-miss* (1+ *cs-created-miss*))
      )
    )
  )
  res
)

;; Набор карты: только созданные отрисовкой объекты (и ещё живые)
(defun cs-ss-from-created (/ ss ent)
  (setq ss (ssadd))
  (foreach ent *cs-created*
    (if (entget ent) (ssadd ent ss))
  )
  ss
)

(defun cs-ss-type-tally (ss / i ent typ rec out)
  (setq out '() i 0)
  (if ss
    (repeat (sslength ss)
      (setq ent (ssname ss i))
      (setq typ (cs-type-key (cdr (assoc 0 (entget ent)))))
      (setq rec (assoc typ out))
      (if rec
        (setq out (subst (cons typ (1+ (cdr rec))) rec out))
        (setq out (append out (list (cons typ 1))))
      )
      (setq i (1+ i))
    )
  )
  out
)

;; Состав одной строкой: "LINE 12, LWPOLYLINE 40, TEXT 33"
(defun cs-tally-str (tally / s rec)
  (setq s "")
  (foreach rec tally
    (setq s (strcat s (if (= s "") "" ", ")
                    (car rec) " " (itoa (cdr rec)))))
  s
)

(defun cs-tally-sort (tally)
  (vl-sort (mapcar '(lambda (x) (cons (car x) (cdr x))) tally)
    '(lambda (a b) (< (car a) (car b))))
)

(defun cs-tally-equal-p (a b)
  (equal (cs-tally-sort a) (cs-tally-sort b))
)

;; Типы, которые ActiveX не копирует в определение блока по отдельности:
;; их владелец — INSERT/POLYLINE, чужой владелец отвергается с ошибкой
;; «Недопустимый объект-владелец» (именно она валила упаковку карты).
(defun cs-copyable-p (ent / k)
  (setq k (if (entget ent) (cs-type-key (cdr (assoc 0 (entget ent)))) "?"))
  (not (member k '("ATTRIB" "SEQEND" "VERTEX" "BLOCK" "ENDBLK")))
)

;; Тип объекта внутри блока: тем же способом, что и у набора карты
;; (DXF-код 0 через ename); ObjectName — только запасной путь.
(defun cs-object-type-key (obj / e typ)
  (setq typ nil)
  (setq e (vl-catch-all-apply 'vlax-vla-object->ename (list obj)))
  (if (not (vl-catch-all-error-p e))
    (setq typ (cs-type-key (cdr (assoc 0 (entget e)))))
  )
  (if (or (null typ) (= typ ""))
    (setq typ (cs-type-key (vl-catch-all-apply 'vla-get-ObjectName (list obj))))
  )
  (if (or (null typ) (= typ "")) "?" typ)
)

;; Состав определения блока (ActiveX-обход): (ВСЕГО ТИП . КОЛИЧЕСТВО ...)
(defun cs-block-type-tally (blockName / acad doc blocks blk obj n out typ rec)
  (setq acad (vl-catch-all-apply 'vlax-get-acad-object '()))
  (if (vl-catch-all-error-p acad)
    nil
    (progn
      (setq doc (vl-catch-all-apply 'vla-get-ActiveDocument (list acad)))
      (if (vl-catch-all-error-p doc)
        nil
        (progn
          (setq blocks (vl-catch-all-apply 'vla-get-Blocks (list doc)))
          (setq blk
            (if (vl-catch-all-error-p blocks)
              nil
              (vl-catch-all-apply 'vla-Item (list blocks blockName))))
          (if (vl-catch-all-error-p blk)
            nil
            (progn
              (setq n 0 out '())
              (vlax-for obj blk
                (setq n (1+ n))
                (setq typ (cs-object-type-key obj))
                (setq rec (assoc typ out))
                (if rec
                  (setq out (subst (cons typ (1+ (cdr rec))) rec out))
                  (setq out (append out (list (cons typ 1))))
                )
              )
              (cons n out)
            )
          )
        )
      )
    )
  )
)

;; Имя владельца объекта: слой/пространство/определение блока — диагностика.
;; Код 330 возвращает то handle-строку, то имя объекта (зависит от контекста),
;; поэтому обрабатываются оба случая. Только чтение, все вызовы под защитой.
(defun cs-owner-name (ent / d h oe od name)
  (setq name nil)
  (setq d (vl-catch-all-apply 'entget (list ent)))
  (if (not (vl-catch-all-error-p d))
    (progn
      (setq h (cdr (assoc 330 d)))
      (cond
        ((= (type h) 'ENAME) (setq oe h))
        ((= (type h) 'STR)
         (setq oe (vl-catch-all-apply 'handent (list h)))
         (if (vl-catch-all-error-p oe) (setq oe nil)))
      )
      (if oe
        (progn
          (setq od (vl-catch-all-apply 'entget (list oe)))
          (if (not (vl-catch-all-error-p od))
            (setq name (cdr (assoc 2 od)))
          )
        )
      )
    )
  )
  (cond
    ((= (type name) 'STR) name)
    ((= (type h) 'ENAME) (strcat "имя объекта " (cs-safe-str h)))
    ((= (type h) 'STR) (strcat "handle " h))
    (T "?")
  )
)

;; Диагностика: что обход базы затянул бы в блок помимо карты.
;; Только чтение и НИКОГДА не возвращает ошибку наружу: при сбое печатается
;; причина, раскрой продолжается (диагностика не роняет работу).
(defun cs-scan-foreign-entities (from-ent ssNew / ent n typ layer owner)
  (setq n 0)
  (setq ent (vl-catch-all-apply 'entnext
              (if from-ent (list from-ent) '())))
  (while (and ent (not (vl-catch-all-error-p ent)))
    (if (not (ssmemb ent ssNew)) ; ssmemb: встроенная проверка, линейный поиск недопустим
      (progn
        (setq typ   (cs-safe-str (cs-type-key (cdr (assoc 0 (entget ent))))))
        (setq layer (cs-safe-str (cdr (assoc 8 (entget ent)))))
        (setq owner (vl-catch-all-apply 'cs-owner-name (list ent)))
        (if (vl-catch-all-error-p owner)
          (setq owner (strcat "ошибка определения: "
                              (cs-safe-str (vl-catch-all-error-message owner)))))
        (setq n (1+ n))
        (if (<= n 10)
          (princ (strcat "\n[CUTSHEET][SCAN] посторонний объект в цепочке БД: "
                         typ " (слой " layer ", владелец " (cs-safe-str owner) ")")))
      )
    )
    (setq ent (vl-catch-all-apply 'entnext (list ent)))
  )
  (if (and ent (vl-catch-all-error-p ent))
    (princ (strcat "\n[CUTSHEET][SCAN] Обход прерван: "
                   (cs-safe-str (vl-catch-all-error-message ent)))))
  (if (> n 0)
    (princ (strcat "\n[CUTSHEET][SCAN] Посторонних объектов в цепочке БД: "
                   (itoa n) " — в блок карты не берутся."))
    (princ "\n[CUTSHEET][SCAN] Посторонних объектов в цепочке БД нет."))
  n
)

;; ================= ГРАФИКА =================
(defun cs-ensure-italic-style (/ result)
  (if (tblsearch "STYLE" "Раскрой Italic") T
    (progn
      (setq result (entmake (list '(0 . "STYLE") '(100 . "AcDbSymbolTableRecord")
                                  '(100 . "AcDbTextStyleTableRecord")
                                  '(2 . "Раскрой Italic") '(70 . 0)
                                  '(40 . 0.0) '(41 . 1.0) '(50 . 0.26)
                                  '(71 . 0) '(42 . 2.5) '(3 . "Arial") '(4 . ""))))
      (if result (tblsearch "STYLE" "Раскрой Italic") nil))))

(defun cs-ensure-bold-style (/ result)
  (if (tblsearch "STYLE" "Основной стиль (надписи без наклона)") T
    (progn
      (setq result (entmake (list '(0 . "STYLE") '(100 . "AcDbSymbolTableRecord")
                                  '(100 . "AcDbTextStyleTableRecord")
                                  '(2 . "Основной стиль (надписи без наклона)")
                                  '(70 . 0) '(40 . 0.0) '(41 . 1.0) '(50 . 0.0)
                                  '(71 . 0) '(42 . 2.5) '(3 . "arialbd.ttf") '(4 . ""))))
      (if result (tblsearch "STYLE" "Основной стиль (надписи без наклона)") nil))))

(defun cs-draw-line (p1 p2 color)
  (cs-mk (list '(0 . "LINE") '(100 . "AcDbEntity")
                 (cons 62 color)
                 (cons 10 (list (car p1) (cadr p1) 0.0))
                 (cons 11 (list (car p2) (cadr p2) 0.0)))))

(defun cs-draw-rect (p1 p2 color)
  (cs-mk (list '(0 . "LWPOLYLINE") '(100 . "AcDbEntity")
                 (cons 62 color) '(100 . "AcDbPolyline")
                 '(90 . 4) '(70 . 1)
                 (cons 10 (list (car p1) (cadr p1)))
                 (cons 10 (list (car p2) (cadr p1)))
                 (cons 10 (list (car p2) (cadr p2)))
                 (cons 10 (list (car p1) (cadr p2))))))

;; Прозрачность через ActiveX
(defun cs-apply-transparency (ent val90 / obj r)
  (if ent
    (progn
      (setq obj (vl-catch-all-apply 'vlax-ename->vla-object (list ent)))
      (if (not (vl-catch-all-error-p obj))
        (progn
          (setq r (vl-catch-all-apply 'vlax-put-property (list obj 'EntityTransparency val90)))
          (if (vl-catch-all-error-p r)
            (vl-catch-all-apply 'vlax-put-property (list obj 'Transparency val90)))))))
  ent)

;; transparency: 0.0..1.0 (где 1.0 = 90% прозрачности)
;; ЗАЛИВКА ЧЕРЕЗ SOLID (цвет через entmod)
(defun cs-draw-filled-rect (p1 p2 color transparency / x1 y1 x2 y2 ent res aci edata)
  (setq x1 (car p1) y1 (cadr p1) x2 (car p2) y2 (cadr p2))
  ;; Преобразуем прозрачность 0.0..1.0 в 0..90
  (setq aci (fix (+ 0.5 (* transparency 90.0))))
  (if (> aci 90) (setq aci 90))
  (if (< aci 0) (setq aci 0))
  
  ;; Создаем SOLID БЕЗ кода 62 (через cs-mk — объект попадает в *cs-created*)
  (setq res
    (cs-mk
      (list
        '(0 . "SOLID")
        '(100 . "AcDbEntity")
        '(100 . "AcDbTrace")
        (cons 10 (list x1 y1 0.0))
        (cons 11 (list x2 y1 0.0))
        (cons 12 (list x1 y2 0.0))
        (cons 13 (list x2 y2 0.0))
        '(39 . 0.0)
      )
    )
  )
  
  (if res
    (progn
      (setq ent (entlast))
      ;; Устанавливаем цвет через entmod
      (setq edata (entget ent))
      (entmod (append edata (list (cons 62 color))))
      ;; Устанавливаем прозрачность через ActiveX
      (cs-apply-transparency ent aci)
      ent)
    nil))

;; П2.4а: кэш имён текстовых стилей - tblsearch убран из горячего цикла
;; отрисовки (~260+ вызовов на прогон). Кэш инвалидируется в cutsheet-main
;; перед отрисовкой карты (после cs-ensure-*-style), поэтому резолв всегда
;; идёт по актуальному состоянию таблицы стилей текущего прогона.
(if (null (boundp '*cs-style-cache*)) (setq *cs-style-cache* nil))
(defun cs-text-style (preferred / a s)
  (setq a (assoc preferred *cs-style-cache*))
  (if a
    (cdr a)
    (progn
      (setq s (if (tblsearch "STYLE" preferred) preferred (getvar "TEXTSTYLE")))
      (setq *cs-style-cache* (cons (cons preferred s) *cs-style-cache*))
      s)))

(defun cs-draw-text (pt h txt color / style)
  (setq style (cs-text-style "Раскрой Italic"))
  (cs-mk (list '(0 . "TEXT") '(100 . "AcDbEntity")
                 (cons 62 color) (cons 7 style)
                 (cons 10 (list (car pt) (cadr pt) 0.0))
                 (cons 40 h) (cons 1 txt) '(50 . 0.0))))

(defun cs-draw-text-bold (pt h txt color / style)
  (setq style (cs-text-style "Основной стиль (надписи без наклона)"))
  (cs-mk (list '(0 . "TEXT") '(100 . "AcDbEntity")
                 (cons 62 color) (cons 7 style)
                 (cons 10 (list (car pt) (cadr pt) 0.0))
                 (cons 40 h) (cons 1 txt) '(50 . 0.0))))

(defun cs-draw-text-center (pt h txt color / style)
  (setq style (cs-text-style "Раскрой Italic"))
  (cs-mk (list '(0 . "TEXT") '(100 . "AcDbEntity")
                 (cons 62 color) (cons 7 style)
                 (cons 10 (list (car pt) (cadr pt) 0.0))
                 (cons 11 (list (car pt) (cadr pt) 0.0))
                 (cons 40 h) (cons 1 txt) '(50 . 0.0)
                 '(72 . 1) '(73 . 2))))

(defun cs-build-color-map (groups / out i g)
  (setq out '() i 0)
  (foreach g groups
    (setq out (cons (cons (car g) (nth (rem i (length *CUTSHEET-PALETTE*)) *CUTSHEET-PALETTE*)) out) i (1+ i)))
  out)

(defun cs-color-for-part (r colorMap / a)
  (setq a (assoc (cs-part-key r) colorMap))
  (if a (cdr a) *CUTSHEET-PART-TEXT-COLOR*))

(defun cs-draw-sheet-header (x y sheetW sheetH n / h textY)
  (setq h *CUTSHEET-SHEET-HEADER*)
  (cs-draw-text-bold (list x (+ y sheetH (* h 0.5))) *CUTSHEET-TEXT-H*
                     (strcat "ЛИСТ " (itoa n)) *CUTSHEET-HEADER-COLOR*)
  (cs-draw-text (list x (+ y sheetH (* h 0.15))) (* *CUTSHEET-TEXT-H* 0.75)
                (cs-itoa-safe sheetH) *CUTSHEET-VALUE-COLOR*)
  (cs-draw-line (list x y) (list (+ x sheetW) y) *CUTSHEET-OUTLINE-COLOR*)
  (setq textY (- y (* h 0.35)))
  (cs-draw-text (list x textY) (* *CUTSHEET-TEXT-H* 0.75) "0" *CUTSHEET-VALUE-COLOR*)
  (cs-draw-text (list (+ x sheetW -140.0) textY) (* *CUTSHEET-TEXT-H* 0.75)
                (cs-itoa-safe sheetW) *CUTSHEET-VALUE-COLOR*))

;; ОТРИСОВКА ИЗДЕЛИЯ: Заливка SOLID + Обводка + Подпись
(defun cs-draw-placement (pl x0 y0 colorMap / r x y w h rot col mk mkH
                                               drawMk sizeH sizeY)
  (setq r (car pl)
        x (+ x0 (cadr pl))
        y (+ y0 (caddr pl))
        w (nth 3 pl)
        h (nth 4 pl)
        rot (nth 5 pl)
        col (cs-color-for-part r colorMap))
  ;; 1. Заливка (под обводкой) — SOLID с прозрачностью
  (cs-draw-filled-rect (list x y) (list (+ x w) (+ y h)) col *CUTSHEET-PART-TRANSPARENCY*)
  ;; 2. Обводка (поверх заливки)
  (cs-draw-rect (list x y) (list (+ x w) (+ y h)) *CUTSHEET-OUTLINE-COLOR*)
  ;; 3. Подпись
  ;; 3-4. Подпись габарита и марка. Марка считается ПЕРВОЙ: от неё
  ;; зависит, куда встанет габарит, иначе на приплюснутых деталях
  ;; подписи наползают друг на друга.
  (setq mk (cs-part-mark r))
  (setq mkH (if mk (min (* *CUTSHEET-TEXT-H* 0.55) (* 0.085 (min w h))) 0.0))
  ;; порог читаемости: мельче четверти основной высоты текста подпись
  ;; на карте уже не читается — лучше не рисовать совсем
  (setq drawMk (and mk
                    (> mkH (* *CUTSHEET-TEXT-H* 0.25))
                    (> w (* (strlen mk) mkH 0.8))
                    (> h (* mkH 3.0))))
  (setq sizeH (min *CUTSHEET-TEXT-H* (* 0.12 (min w h))))
  ;; базовая линия габарита: обычное место, но не ниже строки марки
  (setq sizeY (if drawMk
                (max (* h 0.53) (+ (* mkH 1.5) (* sizeH 0.5)))
                (* h 0.53)))
  ;; если из-за марки габарит вылезает за деталь — снимаем МАРКУ,
  ;; размер детали важнее её обозначения
  (if (and drawMk (> (+ sizeY sizeH) h))
    (setq drawMk nil sizeY (* h 0.53)))
  (if (> (* w h) *CUTSHEET-MIN-TEXT-AREA*)
    (cs-draw-text-center (list (+ x (* w 0.5)) (+ y sizeY))
                         sizeH
                         (cs-part-label r) *CUTSHEET-PART-TEXT-COLOR*))
  (if drawMk
    (cs-draw-text (list (+ x (* mkH 0.5)) (+ y (* mkH 0.5)))
                  mkH mk *CUTSHEET-MARK-COLOR*)))

(defun cs-draw-summary (groups sheets oversized sheetW sheetH rotateFlag insPt kerf / left top width rowH rows y totalCnt actualArea bboxArea sheetArea kpdFact kpdBox waste colorMap maxLabelLen col i sortedGroups sizeStr skipGroups g hasMarks colMark colCnt colArea gMarks gCnt marked rowsList rw m)
  (setq left (car insPt) top (cadr insPt) rowH 160.0 totalCnt 0 actualArea 0.0 bboxArea 0.0
        sheetArea (* (length sheets) sheetW sheetH (/ 1.0 1000000.0)))
  (foreach rec groups (setq totalCnt (+ totalCnt (nth 6 rec)) bboxArea (+ bboxArea (nth 7 rec))
                            actualArea (+ actualArea (nth 8 rec))))
  (setq kpdFact (if (> sheetArea 0.0) (* 100.0 (/ actualArea sheetArea)) 0.0)
        kpdBox (if (> sheetArea 0.0) (* 100.0 (/ bboxArea sheetArea)) 0.0)
        waste (max 0.0 (- sheetArea actualArea)))
  ;; Колонка «Марка» появляется, только если марки есть хотя бы у одной
  ;; группы. Ширина таблицы не меняется: колонки сдвигаются.
  (setq hasMarks nil)
  (foreach rec groups
    (if (and (> (length rec) 9) (nth 9 rec)) (setq hasMarks T)))
  (setq colMark 0.30 colCnt (if hasMarks 0.62 0.45) colArea (if hasMarks 0.80 0.70))
  (setq rows (length groups) maxLabelLen 10)
  (foreach rec groups (setq col (strcat (cs-itoa-safe (nth 4 rec)) "x" (cs-itoa-safe (nth 5 rec))))
    (if (> (strlen col) maxLabelLen) (setq maxLabelLen (strlen col))))
  (setq width (max *CUTSHEET-SUMMARY-W* (+ 600.0 (* maxLabelLen 40.0))))
  ;; ВНИМАНИЕ: внутренняя рамка колонки НЕ рисуется здесь расчетной формулой -
  ;; она строится в конце функции по фактической нижней линии текста,
  ;; иначе секция "НЕРАЗМЕЩЕНО" (её высота меняется) оказывается зачеркнутой.
  
  (setq y (- top (* rowH 0.72)))
  (cs-draw-text-bold (list (+ left 50.0) y) (* *CUTSHEET-TEXT-H* 1.45) "РАСКРОЙ ЛИСТА" *CUTSHEET-TITLE-COLOR*)
  (setq y (- y (* rowH 1.28)))
  (cs-draw-text (list (+ left 50.0) y) *CUTSHEET-TEXT-H*
                (strcat "Лист: " (cs-itoa-safe sheetW) " x " (cs-itoa-safe sheetH) " мм") *CUTSHEET-HEADER-COLOR*)
  (setq y (- y rowH))
  (cs-draw-text (list (+ left 50.0) y) *CUTSHEET-TEXT-H*
                (strcat "Листов: " (itoa (length sheets))) *CUTSHEET-VALUE-COLOR*)
  (setq y (- y rowH))
  (cs-draw-text (list (+ left 50.0) y) *CUTSHEET-TEXT-H*
                (strcat "Изделий: " (itoa totalCnt) " шт.") *CUTSHEET-VALUE-COLOR*)
  (setq y (- y rowH))
  (cs-draw-text (list (+ left 50.0) y) *CUTSHEET-TEXT-H*
                (strcat "Пропил: "
                        (if (= kerf (float (fix kerf))) (itoa (fix kerf)) (rtos kerf 2 1))
                        " мм") *CUTSHEET-VALUE-COLOR*)
  (setq y (- y rowH))
  (cs-draw-text (list (+ left 50.0) y) *CUTSHEET-TEXT-H*
                (if rotateFlag "Поворот деталей разрешен" "Поворот деталей запрещен") *CUTSHEET-VALUE-COLOR*)
  (setq y (- y rowH))
  (cs-draw-text (list (+ left 50.0) y) *CUTSHEET-TEXT-H*
                (strcat "Фактическая площадь: " (cs-format-num actualArea 2) " м2") *CUTSHEET-VALUE-COLOR*)
  (setq y (- y rowH))
  (cs-draw-text (list (+ left 50.0) y) *CUTSHEET-TEXT-H*
                (strcat "Площадь габаритов: " (cs-format-num bboxArea 2) " м2") *CUTSHEET-VALUE-COLOR*)
  (setq y (- y rowH))
  (cs-draw-text-bold (list (+ left 50.0) y) *CUTSHEET-TEXT-H*
                     (strcat "ПОЛЕЗНЫЙ ВЫХОД: " (cs-format-num kpdFact 1) "%") *CUTSHEET-KPD-COLOR*)
  (setq y (- y rowH))
  (cs-draw-text (list (+ left 50.0) y) *CUTSHEET-TEXT-H*
                (strcat "Габаритный выход: " (cs-format-num kpdBox 1) "%") *CUTSHEET-VALUE-COLOR*)
  (setq y (- y rowH))
  (cs-draw-text (list (+ left 50.0) y) *CUTSHEET-TEXT-H*
                (strcat "Потери: " (cs-format-num waste 2) " м2") *CUTSHEET-WASTE-COLOR*)
  (setq y (- y (* 1.2 rowH)))
  (cs-draw-text-bold (list (+ left 50.0) y) *CUTSHEET-TEXT-H* "ИЗДЕЛИЯ (ВхШ)" *CUTSHEET-TITLE-COLOR*)
  (setq y (- y rowH))
  (cs-draw-text (list (+ left 50.0) y) (* *CUTSHEET-TEXT-H* 0.82) "Размер" *CUTSHEET-HEADER-COLOR*)
  (if hasMarks
    (cs-draw-text (list (+ left (* width colMark)) y) (* *CUTSHEET-TEXT-H* 0.82) "Марка" *CUTSHEET-HEADER-COLOR*))
  (cs-draw-text (list (+ left (* width colCnt)) y) (* *CUTSHEET-TEXT-H* 0.82) "Кол-во" *CUTSHEET-HEADER-COLOR*)
  (cs-draw-text (list (+ left (* width colArea)) y) (* *CUTSHEET-TEXT-H* 0.82) "Площадь" *CUTSHEET-HEADER-COLOR*)
  (setq y (- y rowH))
  
  (if rotateFlag
    (setq sortedGroups (vl-sort groups
      '(lambda (a b)
         (cond
           ((< (min (nth 4 a) (nth 5 a)) (min (nth 4 b) (nth 5 b))) T)
           ((> (min (nth 4 a) (nth 5 a)) (min (nth 4 b) (nth 5 b))) nil)
           ((< (max (nth 4 a) (nth 5 a)) (max (nth 4 b) (nth 5 b))) T)
           (T nil)))))
    (setq sortedGroups (vl-sort groups
      '(lambda (a b)
         (cond
           ((< (nth 5 a) (nth 5 b)) T)
           ((> (nth 5 a) (nth 5 b)) nil)
           ((< (nth 4 a) (nth 4 b)) T)
           (T nil))))))
  
  (setq colorMap (cs-build-color-map groups))
  (setq i 0)
  (foreach rec sortedGroups
    (setq col (nth (rem i (length *CUTSHEET-PALETTE*)) *CUTSHEET-PALETTE*))
    (if rotateFlag
      (setq sizeStr (strcat (cs-itoa-safe (min (nth 4 rec) (nth 5 rec))) "x"
                            (cs-itoa-safe (max (nth 4 rec) (nth 5 rec)))))
      (setq sizeStr (strcat (cs-itoa-safe (nth 5 rec)) "x" (cs-itoa-safe (nth 4 rec)))))
    ;; Одна строка на марку. Изделия без марки — отдельной строкой с
    ;; прочерком, чтобы было видно и сколько их.
    (setq gMarks (if (> (length rec) 9) (nth 9 rec) '()))
    (setq gCnt (nth 6 rec) marked 0)
    (foreach m gMarks (setq marked (+ marked (cdr m))))
    (setq rowsList '())
    (if (null gMarks)
      (setq rowsList (list (cons "" gCnt)))
      (progn
        (foreach m gMarks (setq rowsList (append rowsList (list m))))
        (if (> (- gCnt marked) 0)
          (setq rowsList (append rowsList (list (cons "-" (- gCnt marked))))))))
    (foreach rw rowsList
      (cs-draw-text (list (+ left 50.0) y) (* *CUTSHEET-TEXT-H* 0.82) sizeStr col)
      (if hasMarks
        (cs-draw-text (list (+ left (* width colMark)) y) (* *CUTSHEET-TEXT-H* 0.82)
                      (tu-marks-brief (list (car rw))
                                      (tu-fit-chars (* (- colCnt colMark) width)
                                                    (* *CUTSHEET-TEXT-H* 0.82)))
                      *CUTSHEET-VALUE-COLOR*))
      (cs-draw-text (list (+ left (* width colCnt)) y) (* *CUTSHEET-TEXT-H* 0.82)
                    (itoa (cdr rw)) *CUTSHEET-VALUE-COLOR*)
      ;; площадь строки — доля площади группы по количеству
      (cs-draw-text (list (+ left (* width colArea)) y) (* *CUTSHEET-TEXT-H* 0.82)
                    (cs-format-num (if (> gCnt 0)
                                     (* (nth 8 rec) (/ (float (cdr rw)) (float gCnt)))
                                     0.0) 2)
                    *CUTSHEET-VALUE-COLOR*)
      (setq y (- y rowH)))
    (setq i (1+ i)))
  
  ;; Этап 2: секция неразмещенных - агрегировано по габариту:
  ;; заголовок «НЕРАЗМЕЩЕНО (ВxШ)», колонки «габариты | количество».
  (setq skipGroups nil)
  (if oversized
    (progn
      (foreach r oversized
        (setq g (assoc (cs-part-label r) skipGroups))
        (if g
          (setq skipGroups
                (subst (list (car g) (cadr g) (caddr g) (1+ (cadddr g))) g skipGroups))
          (setq skipGroups
                (cons (list (cs-part-label r) (nth 4 r) (nth 5 r) 1) skipGroups))))
      (setq skipGroups
        (vl-sort skipGroups
          '(lambda (a b)
             (cond ((> (* (cadr a) (caddr a)) (* (cadr b) (caddr b))) T)
                   ((< (* (cadr a) (caddr a)) (* (cadr b) (caddr b))) nil)
                   ((vl-string< (car a) (car b)) T)
                   (T nil)))))
      (setq y (- y rowH))
      (cs-draw-text-bold (list (+ left 50.0) y) *CUTSHEET-TEXT-H*
                         "НЕРАЗМЕЩЕНО (ВxШ)" *CUTSHEET-TITLE-COLOR*)
      (setq y (- y rowH))
      (cs-draw-text (list (+ left 50.0) y) (* *CUTSHEET-TEXT-H* 0.82)
                    "Размер" *CUTSHEET-HEADER-COLOR*)
      (cs-draw-text (list (+ left (* width 0.45)) y) (* *CUTSHEET-TEXT-H* 0.82)
                    "Кол-во" *CUTSHEET-HEADER-COLOR*)
      (foreach g skipGroups
        (setq y (- y rowH))
        (cs-draw-text (list (+ left 50.0) y) (* *CUTSHEET-TEXT-H* 0.82)
                      (car g) *CUTSHEET-WASTE-COLOR*)
        (cs-draw-text (list (+ left (* width 0.45)) y) (* *CUTSHEET-TEXT-H* 0.82)
                      (itoa (nth 3 g)) *CUTSHEET-WASTE-COLOR*))))
  
  ;; Внутренняя рамка колонки и возвращаемый bbox - по фактической нижней
  ;; линии текста (запас 0.8 строки): секция неразмещенных целиком внутри.
  (cs-draw-rect (list left (- y (* rowH 0.8)))
                (list (+ left width) top) *CUTSHEET-OUTLINE-COLOR*)
  (list (list left (- y (* rowH 0.8))) (list (+ left width) top)))

;; Фактический объемлющий прямоугольник всех примитивов набора.
;; Рамка результата строится по реальным границам (GetBoundingBox),
;; а не по расчетным координатам - наложение кромки исключено.
;; SAFEARRAY превращается в список точек независимо от того,
;; как отдал параметры AutoCAD: SAFEARRAY напрямую или VARIANT(safearray).
(defun cs-point-array->list (v)
  (cond ((= (type v) 'SAFEARRAY) (vlax-safearray->list v))
        ((= (type v) 'VARIANT)
         (if (= (type (vlax-variant-value v)) 'SAFEARRAY)
           (vlax-safearray->list (vlax-variant-value v))))
        ((= (type v) 'LIST) v)
        (T nil)))

(defun cs-entities-bbox (ss / i e o mn mx x1 y1 x2 y2 pgi pgn)
  (setq x1 nil)
  (setq pgi 0 pgn (sslength ss))
  (setq i 0)
  (repeat (sslength ss)
    (setq e (ssname ss i))
    (setq pgi (1+ pgi))
    (if (= 0 (rem pgi 50))
      (grtext -1 (strcat "CUTSHEET: bbox " (itoa pgi) " из " (itoa pgn))))
    (setq o (vl-catch-all-apply 'vlax-ename->vla-object (list e)))
    (if (and (not (vl-catch-all-error-p o)) o)
      (progn
        ;; П2.2 (принято): vla-update здесь НЕ нужен и был дорог - замер
        ;; [PERF] CUTSHEET:bbox: 2578 -> 532 ms на 743 примитива (x4.8).
        ;; GetBoundingBox сразу после entmake даёт корректные границы:
        ;; рамка не режет тексты шапок, [wrap]-контракт 0/1 подтверждён.
        (setq mn nil)
        (setq mx nil)
        (vl-catch-all-apply 'vla-GetBoundingBox (list o 'mn 'mx))
        (setq mn (cs-point-array->list mn))
        (setq mx (cs-point-array->list mx))
        (if (and mn mx)
          (progn
            (if (or (null x1) (< (car mn) x1)) (setq x1 (car mn)))
            (if (or (null y1) (< (cadr mn) y1)) (setq y1 (cadr mn)))
            (if (or (null x2) (> (car mx) x2)) (setq x2 (car mx)))
            (if (or (null y2) (> (cadr mx) y2)) (setq y2 (cadr mx)))
          )
        )
      )
    )
    (setq i (1+ i))
  )
  (if x1 (list (list x1 y1) (list x2 y2)) nil)
)

(defun cs-draw-frame (bbox / x1 y1 x2 y2)
  (if (not (tblsearch "LAYER" *CUTSHEET-FRAME-LAYER*))
    (entmake (list '(0 . "LAYER") '(100 . "AcDbSymbolTableRecord")
                   '(100 . "AcDbLayerTableRecord")
                   (cons 2 *CUTSHEET-FRAME-LAYER*) '(70 . 0)
                   '(62 . 7) '(6 . "Continuous") '(370 . -3))))
  (setq x1 (- (car (car bbox)) *CUTSHEET-FRAME-PAD-LEFT*)
        y1 (- (cadr (car bbox)) *CUTSHEET-FRAME-PAD-BOTTOM*)
        x2 (+ (car (cadr bbox)) *CUTSHEET-FRAME-PAD-RIGHT*)
        y2 (+ (cadr (cadr bbox)) *CUTSHEET-FRAME-PAD-TOP*))
  (cs-mk (list '(0 . "LWPOLYLINE") '(100 . "AcDbEntity")
               (cons 8 *CUTSHEET-FRAME-LAYER*) '(100 . "AcDbPolyline")
                 '(90 . 4) '(70 . 1)
                 (cons 10 (list x1 y1)) (cons 10 (list x2 y1))
                 (cons 10 (list x2 y2)) (cons 10 (list x1 y2))))
  (list (list x1 y1) (list x2 y2)))

(defun cs-draw-layout (sheets sheetW sheetH insPt colorMap / n sh col row x y p pgi pgn)
  ;; П3 (п.20): прогресс в статусной строке (grtext -1 не скроллит командную строку)
  (setq n 0)
  (setq pgi 0 pgn (length sheets))
  (foreach sh sheets
    (setq pgi (1+ pgi))
    (grtext -1 (strcat "CUTSHEET: отрисовка листа " (itoa pgi) " из " (itoa pgn)))
    (setq n (1+ n) col (rem (1- n) *CUTSHEET-GRID-COLS*)
          row (fix (/ (1- n) *CUTSHEET-GRID-COLS*))
          x (+ (car insPt) (* col (+ sheetW *CUTSHEET-SHEET-GAP*)))
          y (- (cadr insPt) (* row (+ sheetH *CUTSHEET-SHEET-GAP* *CUTSHEET-SHEET-HEADER*))))
    (cs-draw-sheet-header x y sheetW sheetH n)
    (cs-draw-rect (list x y) (list (+ x sheetW) (+ y sheetH)) *CUTSHEET-OUTLINE-COLOR*)
    (foreach p (cadr sh) (cs-draw-placement p x y colorMap)))
  (list (list (car insPt) (- (cadr insPt) (* (max 0 (fix (/ (max 0 (1- n)) *CUTSHEET-GRID-COLS*)))
                                              (+ sheetH *CUTSHEET-SHEET-GAP* *CUTSHEET-SHEET-HEADER*))))
        (list (+ (car insPt) (* (max 0 (1- (min n *CUTSHEET-GRID-COLS*))) (+ sheetW *CUTSHEET-SHEET-GAP*)) sheetW)
              (+ (cadr insPt) sheetH))))

;; ================= XLS / CSV =================
(defun cs-write-csv (sheets oversized sheetW sheetH kerf / fname f n sh p r hasMarks mk)
  (setq fname (strcat (getvar "DWGPREFIX") (vl-filename-base (getvar "DWGNAME")) " Раскрой листа.csv"))
  (setq f (open fname "w"))
  (if f
    (progn
      (setq hasMarks (cs-xls-has-marks sheets oversized))
      (write-line "Раскрой листа" f)
      (write-line (strcat "Лист;" (cs-itoa-safe sheetW) "x" (cs-itoa-safe sheetH) ";Пропил;" (cs-format-num kerf 2)) f)
      (write-line (if hasMarks
                    "№ листа;№ детали;Размер;Тип;Марка;X;Y;Поворот;Площадь, м2"
                    "№ листа;№ детали;Размер;Тип;X;Y;Поворот;Площадь, м2") f)
      (setq n 0)
      (foreach sh sheets
        (setq n (1+ n))
        (foreach p (cadr sh)
          (setq r (car p) mk (cs-part-mark r))
          (write-line (strcat (itoa n) ";" (itoa (car r)) ";" (cs-part-label r) ";" (cs-part-type r) ";"
                              (if hasMarks (strcat (if mk mk "") ";") "")
                              (cs-format-num (nth 1 p) 1) ";" (cs-format-num (nth 2 p) 1) ";"
                              (if (= (nth 5 p) 1) "90" "0") ";" (cs-format-num (nth 6 r) 4)) f)))
      (if oversized
        (progn
          (write-line "" f)
          (write-line "НЕРАЗМЕЩЕННЫЕ ДЕТАЛИ" f)
          (foreach r oversized
            (setq mk (cs-part-mark r))
            (write-line (strcat (itoa (car r)) ";" (cs-part-label r) ";" (cs-part-type r) ";"
                                (if hasMarks (strcat (if mk mk "") ";") "")
                                (cs-format-num (nth 6 r) 4)) f))))
      (close f)
      (princ (strcat "\nCSV сохранен: " fname))
      T)
    nil))

(defun cs-write-xls (groups sheets oversized sheetW sheetH kerf /
                      fname f n sh p r rec totalCnt actualArea bboxArea sheetArea
                      kpdFact kpdBox hasMarks mk gMarks gCnt marked rowsList rw)
  (setq fname (strcat (getvar "DWGPREFIX") (vl-filename-base (getvar "DWGNAME")) " Раскрой листа.xls"))
  (setq f (open fname "w"))
  (if f
    (progn
      (setq totalCnt 0 actualArea 0.0 bboxArea 0.0)
      (setq hasMarks (cs-xls-has-marks sheets oversized))
      (foreach rec groups (setq totalCnt (+ totalCnt (nth 6 rec)) bboxArea (+ bboxArea (nth 7 rec))
                                actualArea (+ actualArea (nth 8 rec))))
      (setq sheetArea (* (length sheets) sheetW sheetH (/ 1.0 1000000.0))
            kpdFact (if (> sheetArea 0.0) (* 100.0 (/ actualArea sheetArea)) 0.0)
            kpdBox  (if (> sheetArea 0.0) (* 100.0 (/ bboxArea sheetArea)) 0.0))
      (eu-doc-begin f "BASIC")
(write-line "<Styles>" f)
      (write-line "<Style ss:ID=\"Default\"><Alignment ss:Vertical=\"Center\"/></Style>" f)
      (write-line "<Style ss:ID=\"T\"><Font ss:Bold=\"1\" ss:Size=\"13\"/><Interior ss:Color=\"#D9D9D9\" ss:Pattern=\"Solid\"/><Alignment ss:Horizontal=\"Center\" ss:Vertical=\"Center\"/><Borders><Border ss:Position=\"Bottom\" ss:LineStyle=\"Continuous\" ss:Weight=\"1\"/><Border ss:Position=\"Left\" ss:LineStyle=\"Continuous\" ss:Weight=\"1\"/><Border ss:Position=\"Right\" ss:LineStyle=\"Continuous\" ss:Weight=\"1\"/><Border ss:Position=\"Top\" ss:LineStyle=\"Continuous\" ss:Weight=\"1\"/></Borders></Style>" f)
      (write-line "<Style ss:ID=\"H\"><Font ss:Bold=\"1\"/><Interior ss:Color=\"#D9D9D9\" ss:Pattern=\"Solid\"/><Alignment ss:Horizontal=\"Center\" ss:Vertical=\"Center\"/><Borders><Border ss:Position=\"Bottom\" ss:LineStyle=\"Continuous\" ss:Weight=\"1\"/><Border ss:Position=\"Left\" ss:LineStyle=\"Continuous\" ss:Weight=\"1\"/><Border ss:Position=\"Right\" ss:LineStyle=\"Continuous\" ss:Weight=\"1\"/><Border ss:Position=\"Top\" ss:LineStyle=\"Continuous\" ss:Weight=\"1\"/></Borders></Style>" f)
      (write-line "<Style ss:ID=\"D\"><Alignment ss:Vertical=\"Center\"/><Borders><Border ss:Position=\"Bottom\" ss:LineStyle=\"Continuous\" ss:Weight=\"1\"/><Border ss:Position=\"Left\" ss:LineStyle=\"Continuous\" ss:Weight=\"1\"/><Border ss:Position=\"Right\" ss:LineStyle=\"Continuous\" ss:Weight=\"1\"/><Border ss:Position=\"Top\" ss:LineStyle=\"Continuous\" ss:Weight=\"1\"/></Borders></Style>" f)
      (write-line "<Style ss:ID=\"N\"><NumberFormat ss:Format=\"0.00\"/><Alignment ss:Vertical=\"Center\"/><Borders><Border ss:Position=\"Bottom\" ss:LineStyle=\"Continuous\" ss:Weight=\"1\"/><Border ss:Position=\"Left\" ss:LineStyle=\"Continuous\" ss:Weight=\"1\"/><Border ss:Position=\"Right\" ss:LineStyle=\"Continuous\" ss:Weight=\"1\"/><Border ss:Position=\"Top\" ss:LineStyle=\"Continuous\" ss:Weight=\"1\"/></Borders></Style>" f)
      (write-line "</Styles>" f)

      (eu-worksheet f "Итоги")
      ;; С маркой колонок пять: ширина колонки марки добавляется,
      ;; остальные не меняются.
      (eu-column f "220" "0")
      (eu-column f "110" "0")
      (if hasMarks (eu-column f "150" "0"))
      (eu-column f "110" "0")
      (eu-column f "120" "0")

      (eu-row-begin f "")
      (eu-cell f "T" "String" "Раскрой листа"
               (if hasMarks "ss:MergeAcross=\"4\"" "ss:MergeAcross=\"3\""))
      (eu-row-end f)

      (eu-row-begin f "")
      (eu-cell f "D" "String" "Формат листа" "")
      (eu-cell f "D" "String" (strcat (cs-itoa-safe sheetW) "x" (cs-itoa-safe sheetH) " мм") "")
      (eu-row-end f)

      (eu-row-begin f "")
      (eu-cell f "D" "String" "Пропил" "")
      (eu-cell f "N" "Number" (cs-xls-num kerf 2) "")
      (eu-row-end f)

      (eu-row-begin f "")
      (eu-cell f "D" "String" "Листов" "")
      (eu-cell f "D" "Number" (itoa (length sheets)) "")
      (eu-row-end f)

      (eu-row-begin f "")
      (eu-cell f "D" "String" "Изделий" "")
      (eu-cell f "D" "Number" (itoa totalCnt) "")
      (eu-row-end f)

      (eu-row-begin f "")
      (eu-cell f "D" "String" "Фактическая площадь, м2" "")
      (eu-cell f "N" "Number" (cs-xls-num actualArea 4) "")
      (eu-row-end f)

      (eu-row-begin f "")
      (eu-cell f "D" "String" "Площадь габаритов, м2" "")
      (eu-cell f "N" "Number" (cs-xls-num bboxArea 4) "")
      (eu-row-end f)

      (eu-row-begin f "")
      (eu-cell f "H" "String" "Полезный выход, %" "")
      (eu-cell f "H" "Number" (cs-xls-num kpdFact 1) "")
      (eu-row-end f)

      (eu-row-begin f "")
      (eu-cell f "D" "String" "Габаритный выход, %" "")
      (eu-cell f "N" "Number" (cs-xls-num kpdBox 1) "")
      (eu-row-end f)

      (eu-row-begin f "")
      (eu-row-end f)

      (eu-row-begin f "")
      (eu-cell f "H" "String" "Размер" "")
      (eu-cell f "H" "String" "Тип" "")
      (if hasMarks (eu-cell f "H" "String" "Марка" ""))
      (eu-cell f "H" "String" "Кол-во" "")
      (eu-cell f "H" "String" "Площадь, м2" "")
      (eu-row-end f)

      ;; Строка на каждую марку - как в таблице AutoCAD (cs-draw-summary):
      ;; изделия без марки отдельной строкой с прочерком, площадь строки -
      ;; доля площади группы по количеству, поэтому сумма строк равна
      ;; площади группы.
      (foreach rec groups
        (setq gMarks (if (> (length rec) 9) (nth 9 rec) '())
              gCnt (nth 6 rec) marked 0 rowsList '())
        (foreach mk gMarks (setq marked (+ marked (cdr mk))))
        (if (null gMarks)
          (setq rowsList (list (cons "" gCnt)))
          (progn
            (foreach mk gMarks (setq rowsList (append rowsList (list mk))))
            (if (> (- gCnt marked) 0)
              (setq rowsList (append rowsList (list (cons "-" (- gCnt marked))))))))
        (foreach rw rowsList
          (eu-row-begin f "")
          (eu-cell f "D" "String" (strcat (cs-itoa-safe (nth 4 rec)) "x" (cs-itoa-safe (nth 5 rec))) "")
          (eu-cell f "D" "String" (cs-group-type rec) "")
          (if hasMarks (eu-cell f "D" "String" (if (car rw) (car rw) "") ""))
          (eu-cell f "D" "Number" (itoa (cdr rw)) "")
          (eu-cell f "N" "Number" (cs-xls-num (if (> gCnt 0)
                                                (* (nth 8 rec) (/ (float (cdr rw)) (float gCnt)))
                                                0.0) 4) "")
          (eu-row-end f)))
      (eu-worksheet-end f)

      (eu-worksheet f "Размещение")
      (eu-row-begin f "")
      (eu-cell f "T" "String" "Размещение деталей"
               (if hasMarks "ss:MergeAcross=\"8\"" "ss:MergeAcross=\"7\""))
      (eu-row-end f)

      (eu-row-begin f "")
      (eu-cell f "H" "String" "Лист" "")
      (eu-cell f "H" "String" "№" "")
      (eu-cell f "H" "String" "Размер" "")
      (eu-cell f "H" "String" "Тип" "")
      (if hasMarks (eu-cell f "H" "String" "Марка" ""))
      (eu-cell f "H" "String" "X" "")
      (eu-cell f "H" "String" "Y" "")
      (eu-cell f "H" "String" "Поворот" "")
      (eu-cell f "H" "String" "Площадь" "")
      (eu-row-end f)

      (setq n 0)
      (foreach sh sheets
        (setq n (1+ n))
        (foreach p (cadr sh)
          (setq r (car p) mk (cs-part-mark r))
          (eu-row-begin f "")
          (eu-cell f "D" "Number" (itoa n) "")
          (eu-cell f "D" "Number" (itoa (car r)) "")
          (eu-cell f "D" "String" (cs-part-label r) "")
          (eu-cell f "D" "String" (cs-part-type r) "")
          (if hasMarks (eu-cell f "D" "String" (if mk mk "") ""))
          (eu-cell f "N" "Number" (cs-xls-num (nth 1 p) 1) "")
          (eu-cell f "N" "Number" (cs-xls-num (nth 2 p) 1) "")
          (eu-cell f "D" "Number" (if (= (nth 5 p) 1) "90" "0") "")
          (eu-cell f "N" "Number" (cs-xls-num (nth 6 r) 4) "")
          (eu-row-end f)))
      (eu-worksheet-end f)

      (if oversized
        (progn
          (eu-worksheet f "Неразмещенные")
          (eu-row-begin f "")
          (eu-cell f "T" "String" "Неразмещенные детали"
               (if hasMarks "ss:MergeAcross=\"4\"" "ss:MergeAcross=\"3\""))
          (eu-row-end f)
          (foreach r oversized
            (setq mk (cs-part-mark r))
            (eu-row-begin f "")
            (eu-cell f "D" "Number" (itoa (car r)) "")
            (eu-cell f "D" "String" (cs-part-label r) "")
            (eu-cell f "D" "String" (cs-part-type r) "")
            (if hasMarks (eu-cell f "D" "String" (if mk mk "") ""))
            (eu-cell f "N" "Number" (cs-xls-num (nth 6 r) 4) "")
            (eu-row-end f))
          (eu-worksheet-end f)))

      (eu-doc-end f)
      (close f)
      (princ (strcat "\nXLS сохранен: " fname))
      T)
    nil))

;; ================= СЛУЖЕБНЫЕ ГРАФИЧЕСКИЕ ПРОЦЕДУРЫ =================
(defun cs-combine-bbox (a b)
  (list (list (min (car (car a)) (car (car b))) (min (cadr (car a)) (cadr (car b))))
        (list (max (car (cadr a)) (car (cadr b))) (max (cadr (cadr a)) (cadr (cadr b))))))

(defun cs-zoom-bbox (bbox / app p1 p2)
  (setq app (vl-catch-all-apply 'vlax-get-acad-object '()))
  (if (and app bbox)
    (progn
      (setq p1 (vlax-3d-point (list (car (car bbox)) (cadr (car bbox)) 0.0))
            p2 (vlax-3d-point (list (car (cadr bbox)) (cadr (cadr bbox)) 0.0)))
      (vl-catch-all-apply 'vla-ZoomWindow (list app p1 p2)))))

(defun cs-setvar-transparency-display ()
  (vl-catch-all-apply 'setvar (list "TRANSPARENCYDISPLAY" 1)))

(defun cs-unique-block-name (base)
  ;; U3: единый генератор - см. common/task-utils.lsp
  (tu-unique-block-name base))

(defun cs-wrap-to-block (blockName basePt ss / ok r oldRefs si e retained ins-result finalRefs insertPt3 acad doc ms result
                         objList skipped tmpStr blkTally expTally tallyOk)
  ;; П2.3: упаковка набора в блок через ActiveX (замер 5.2: vl-cmdf "_.-BLOCK"
  ;; = 93% стоимости wrap - 1140 мс на 743 примитива). CopyObjects копирует
  ;; набор в определение блока (базовая точка = basePt), оригиналы стираем,
  ;; вставляем ровно один INSERT. Детерминированно, без версионных режимов
  ;; [Преобразовать/Удалить]; UNDO-контракт накрыт V13 снаружи.
  (if (or (null ss) (<= (sslength ss) 0))
    (progn (princ "\n[wrap] Нет объектов для блока.") nil)
    (progn
      ;; Число INSERT имени blockName ДО упаковки (контракт «ровно 1 новый», Шаг 4)
      (pu-begin "CUTSHEET:wrap:ssget")
      (setq r (ssget "_X" (list '(0 . "INSERT") (cons 2 blockName))))
      (pu-end "CUTSHEET:wrap:ssget")
      (setq oldRefs (if r (sslength r) 0))
      (setq acad (vlax-get-acad-object)
            doc  (vla-get-ActiveDocument acad)
            ms   (vla-get-ModelSpace doc))
      (pu-begin "CUTSHEET:wrap:block")
      (setq result
        (vl-catch-all-apply
          '(lambda ( / blocks blkDef arr i o k)
             (setq blocks (vla-get-Blocks doc)
                   blkDef (vla-Add blocks
                                  (vlax-3d-point (list (car basePt) (cadr basePt) 0.0))
                                  blockName))
             ;; Ред. 25: CopyObjects нельзя отдавать ATTRIB/SEQEND/VERTEX —
             ;; у них владелец INSERT/POLYLINE, и ActiveX отвечает
             ;; «Недопустимый объект-владелец», роняя всю упаковку.
             (setq objList '() skipped '() i 0)
             (repeat (sslength ss)
               (setq e (ssname ss i) i (1+ i))
               (setq k (if (entget e)
                         (cs-type-key (cdr (assoc 0 (entget e))))
                         "?"))
               (if (cs-copyable-p e)
                 (progn
                   (setq o (vl-catch-all-apply 'vlax-ename->vla-object (list e)))
                   (if (or (vl-catch-all-error-p o) (null o))
                     (setq skipped (cons k skipped))
                     (setq objList (cons o objList))))
                 (setq skipped (cons k skipped))))
             (setq objList (reverse objList) skipped (reverse skipped))
             (if (null objList)
               nil
               (progn
                 (setq arr (vlax-make-safearray vlax-vbObject
                             (cons 0 (1- (length objList))))
                       i 0)
                 (foreach o objList
                   (vlax-safearray-put-element arr i o)
                   (setq i (1+ i)))
                 (vla-CopyObjects doc arr blkDef)
                 T))))) ; progn, if, lambda, vl-catch-all-apply, setq
      (pu-end "CUTSHEET:wrap:block")
      (cond
        ((vl-catch-all-error-p result)
         (princ (strcat "\n[wrap] Ошибка: " (vl-catch-all-error-message result)))
         (setq ok nil))
        ((not (tblsearch "BLOCK" blockName))
         (princ "\n[wrap] Блок не создан")
         (setq ok nil))
        (T
         (pu-begin "CUTSHEET:wrap:insert")
         (setq ok T)
         (princ (strcat "\n[wrap] Блок создан: да, ссылок: " (itoa oldRefs)))
         (if skipped
           (progn
             (setq tmpStr "")
             (foreach k skipped
               (setq tmpStr (strcat tmpStr (if (= tmpStr "") "" ", ") (cs-safe-str k))))
             (princ (strcat "\n[CUTSHEET][GUARD] в наборе карты несовместимые с блоком объекты, "
                            "они не копировались: " tmpStr))))
         ;; Ред. 25: контроль состава — в определении блока должно лежать ровно
         ;; то, что нарисовала карта. При несовпадении оригиналы НЕ удаляем и
         ;; INSERT не вставляем: данные важнее завершённости операции.
         (setq blkTally (cs-block-type-tally blockName))
         (setq expTally (cs-ss-type-tally ss))
         (setq tallyOk (and blkTally (cs-tally-equal-p (cdr blkTally) expTally)))
         (if tallyOk
           (princ (strcat "\n[CUTSHEET] В блоке объектов: " (itoa (car blkTally))
                          " (карта: " (itoa (sslength ss)) ") — "
                          (cs-tally-str (cdr blkTally))))
           (progn
             (setq ok nil)
             (princ (strcat "\n[CUTSHEET][GUARD] состав блока не совпал с набором карты — "
                            "оригиналы не удалены, INSERT не вставлен: "
                            (if blkTally
                              (strcat "в блоке " (itoa (car blkTally)) " (" (cs-tally-str (cdr blkTally))
                                      "), в наборе " (itoa (sslength ss)) " (" (cs-tally-str expTally) ")")
                              "состав блока недоступен")))))
         (if tallyOk
           (progn
             ;; CopyObjects КОПИРУЕТ: оригиналы в модели больше не нужны
             (setq si 0 retained 0)
             (repeat (sslength ss)
               (setq e (ssname ss si))
               (if (entget e) (progn (entdel e) (setq retained (1+ retained))))
               (setq si (1+ si)))
             (if (> retained 0)
               (princ (strcat "\n[wrap] Удалено оригиналов после копии в блок: " (itoa retained))))
             ;; Вставляем ровно один INSERT обратно в базовую точку
             (setq insertPt3 (vlax-3d-point (list (car basePt) (cadr basePt) 0.0)))
             (setq ins-result (ex-safe-call 'vla-InsertBlock (list ms insertPt3 blockName 1.0 1.0 1.0 0.0)))
             (if (ex-safe-ok-p ins-result)
               (progn
                 (if (= (type ae-settings-output-layer) 'SUBR)
                   (ae-settings-apply-vla-layer
                     (ex-safe-value ins-result)
                     (ae-settings-output-layer 'CUTSHEET)))
                 (princ (strcat "\n[wrap] Блок вставлен в базовую точку: " (rtos (car basePt) 2 2) "," (rtos (cadr basePt) 2 2))))
               (princ (strcat "\n[wrap] ОШИБКА вставки INSERT: " (ex-safe-message ins-result))))
             ;; Контроль (Шаг 4): после упаковки в чертеже ровно один новый INSERT
             (setq r (ssget "_X" (list '(0 . "INSERT") (cons 2 blockName))))
             (setq finalRefs (if r (sslength r) 0))
             (princ (strcat "\n[wrap] Проверка: ссылок до упаковки: " (itoa oldRefs)
                            ", после вставки: " (itoa finalRefs)
                            (if (= finalRefs (1+ oldRefs)) " (OK: ровно 1 новый)" " (ВНИМАНИЕ: прирост не равен 1!)")))))
         (pu-end "CUTSHEET:wrap:insert")))
      ok)))

;; ================= ГЛАВНАЯ ФУНКЦИЯ =================
(defun cutsheet-main (layers-from-caller / *error* ss polyCnt dynCnt dynTypes
                      svSaved
                      defaultW defaultH defaultKerf defaultRotate defaultXls defaultAcad
                      r choice sheetW sheetH kerf rotateFlag exportXls exportAcad dynType
                      records groups parts nested sheets oversized fitSrc impossible
                      insPt colorMap bbox1 bbox2 bbox3 bbox
                      doc oldEcho lastEnt ssNew ent blockName baseName uMark
                      totalCnt actualArea bboxArea sheetArea kpdFact kpdBox
                      blockBasePt oldOsmode oldCmddia oldFiledia bboxFact bboxCalc v5ans
                      srcTitle)
  
  (defun *error* (msg)
    (if (and msg (not (wcmatch (strcase msg) "*CANCEL*,*QUIT*,*BREAK*,*EXIT*")))
      (princ (strcat "\n[CUTSHEET ERROR] " msg)))
    (if uMark (tu-undo-end doc))
    (tu-sysvar-restore svSaved)
    (setq *cs-tmp-choice* 'ALL *cs-tmp-dyn-type* "")
    (princ))
  
  (setq oldOsmode (getvar "OSMODE")
        oldCmddia (getvar "CMDDIA")
        oldFiledia (getvar "FILEDIA")
        oldEcho (getvar "CMDECHO"))
  ;; V8: guard - любой обрыв вернёт исходные значения через *error*
  (setq svSaved (tu-sysvar-save '("CMDECHO" "OSMODE" "CMDDIA" "FILEDIA")))
  (if (= (type ae-settings-output) 'SUBR)
    (setq *CUTSHEET-FRAME-LAYER*
      (ae-settings-output 'CUTSHEET "output.frame.layer"
        *CUTSHEET-FRAME-LAYER*)))
  
  (princ "\n=== РАСКРОЙ ЛИСТА ===")

  ;; Ред. 24: подпись источника слоёв от общей системы фильтров диспетчера
  ;; («по фильтру: Мои» / «по фильтрам: Фасады, Окна»), если слои дал фильтр
  (setq srcTitle nil)
  (if (= (type extraction-layer-filter-source-title) 'SUBR)
    (setq srcTitle (extraction-layer-filter-source-title))
  )
  (if srcTitle
    (princ (strcat "\n" srcTitle))
  )
  
  (if (eq layers-from-caller 'ASK)
    (progn
      (setq layers-from-caller (getstring T "\nСлои через запятую (Enter — все слои): "))
      (if (= layers-from-caller "")
        (setq layers-from-caller nil)
        (setq layers-from-caller
          (mapcar '(lambda (x) (vl-string-trim " \t" x))
                  (cs-split-string layers-from-caller ","))))))
  
  (setq ss (cs-build-filter-ss layers-from-caller))
  (if (null ss)
    (progn (princ "\nНе выбрано подходящих LWPOLYLINE/INSERT.") (princ) (exit)))
  
  (setq polyCnt (cs-count-type ss 'POLY)
        dynCnt (cs-count-type ss 'DYN)
        dynTypes (cs-collect-dyn-types ss))
  
  (princ (strcat "\nПолилиний: " (itoa polyCnt) ", динамических блоков: " (itoa dynCnt)))
  (tu-diag "SCAN" (strcat "объектов в выборке: " (itoa (+ polyCnt dynCnt))))
  
  (if (= (+ polyCnt dynCnt) 0)
    (progn (princ "\nПодходящих исходных объектов нет.") (princ) (exit)))
  
  (setq defaultW *CUTSHEET-LAST-WIDTH*
        defaultH *CUTSHEET-LAST-HEIGHT*
        defaultKerf *CUTSHEET-LAST-KERF*
        defaultRotate *CUTSHEET-LAST-ROTATE*
        defaultXls *CUTSHEET-LAST-XLS*
        defaultAcad *CUTSHEET-LAST-ACAD*)
  
  (if (boundp '*CUTSHEET-CREATE-XLS*) (setq defaultXls *CUTSHEET-CREATE-XLS*))
  (if (boundp '*CUTSHEET-CREATE-TABLE*) (setq defaultAcad *CUTSHEET-CREATE-TABLE*))
  
  (setq r (cs-dialog polyCnt dynCnt dynTypes ss defaultW defaultH defaultKerf defaultRotate defaultXls defaultAcad))
  (if (null r) (progn (princ "\nРаскрой листа отменен.") (princ) (exit)))
  
  (setq choice (nth 0 r) sheetW (nth 1 r) sheetH (nth 2 r) kerf (nth 3 r)
        rotateFlag (nth 4 r) exportXls (nth 5 r) exportAcad (nth 6 r) dynType (nth 7 r))
  
  (setq *CUTSHEET-LAST-WIDTH* sheetW *CUTSHEET-LAST-HEIGHT* sheetH
        *CUTSHEET-LAST-KERF* kerf *CUTSHEET-LAST-ROTATE* rotateFlag
        *CUTSHEET-LAST-XLS* exportXls *CUTSHEET-LAST-ACAD* exportAcad)
  
  (pu-begin "CUTSHEET:collect")
  (setq records (cs-collect-records ss choice dynType))
  (pu-end "CUTSHEET:collect")
  (cs-print-rejects)
  ;; Диагностика заполнения: видно, сколько деталей посчитано по проёму
  ;; и с каким припуском. Маска «*» ловит ВСЕ блоки — предупреждаем.
  (if (> *cs-fill-count* 0)
    (progn
      (princ (strcat "\n[CUTSHEET] Заполнение: " (itoa *cs-fill-count*)
                     " блоков, размер в свету + припуск "
                     (itoa (cs-fill-allowance)) " мм"))
      (if (member "*" (cs-fill-masks))
        (princ (strcat "\n[CUTSHEET][GUARD] Маска блоков ЗАПОЛНЕНИЯ = \"*\": "
                       "припуск применён ко ВСЕМ подходящим блокам. "
                       "Сузьте маску в Настройках, если это не нужно.")))))
  (tu-diag "FILTER" (strcat "принято деталей: " (itoa (length records))
                             ", исключено: " (itoa (apply (quote +) (mapcar (quote cdr) *cs-rejects*)))))

  ;; Этап 2 (V5): мягкий лимит - предупреждение (GUI + командная строка)
  ;; и запрос на продолжение; Нет/Enter = остановка (прежнее поведение).
  (if (> (length records) *cs-max-parts*)
    (progn
      (princ (strcat "\n[CUTSHEET][GUARD] Обнаружено " (itoa (length records))
                      " деталей при лимите " (itoa *cs-max-parts*)
                      ". Проверьте выборку/слои."))
      (alert (strcat "AutoExtraction / CUTSHEET\n\nВ раскрое принято "
                     (itoa (length records)) " деталей при лимите "
                     (itoa *cs-max-parts*) ".\nОбработка может занять очень долгое время.\n\nРешение - в командной строке."))
      (initget "Да Нет _Yes No")
      (setq v5ans (getkword "\nПродолжить обработку несмотря на лимит? [Да/Нет] <Нет>: "))
      (if (= v5ans "Yes")
        (princ "\n[CUTSHEET][GUARD] Продолжаю обработку по явному подтверждению.")
        (progn
          (princ "\n[CUTSHEET][GUARD] Обработка остановлена пользователем.")
          (princ) (exit)))))
  (if (null records)
    (progn (princ "\nПосле фильтрации не осталось деталей с определенными габаритами.")
           (princ) (exit)))
  
  ;; Этап 2 (V7): детали, не помещающиеся на лист ни в одной ориентации,
  ;; отсекаются ДО солвера - не попадают ни в статистику, ни в таблицы,
  ;; только в секции "НЕРАЗМЕЩЕНО" консоли/XLS/CSV.
  (setq fitSrc nil impossible nil)
  (foreach r records
    (if (cs-part-fits-sheet-p (nth 4 r) (nth 5 r) sheetW sheetH rotateFlag)
      (setq fitSrc (cons r fitSrc))
      (setq impossible (cons r impossible))))
  (setq fitSrc (reverse fitSrc) impossible (reverse impossible))
  
  (if (null fitSrc)
    (progn
      (princ (strcat "\nНЕРАЗМЕЩЕНО: " (itoa (length impossible)) " шт."))
      (foreach r impossible
        (princ (strcat "\n  " (cs-part-label r) " | " (nth 3 r))))
      (princ "\nНи одна деталь не помещается на лист. Раскрой невозможен.")
      (princ) (exit)))
  
  (princ (strcat "\nВ раскрой принято деталей: " (itoa (length fitSrc))))
  
  (setq groups (cs-aggregate fitSrc))
  (pu-begin "CUTSHEET:nest")
  (setq nested (cs-nest fitSrc sheetW sheetH kerf rotateFlag)
        sheets (car nested)
        oversized (cadr nested))
  (pu-end "CUTSHEET:nest")
  (setq oversized (append impossible oversized))
  (tu-diag "PACK" (strcat "листов: " (itoa (length sheets)) ", неразмещено записей: " (itoa (length oversized))))
  
  (setq totalCnt (length fitSrc)
        actualArea (cs-total-actual-area-records fitSrc)
        bboxArea (cs-total-bbox-area-records fitSrc)
        sheetArea (* (length sheets) sheetW sheetH (/ 1.0 1000000.0))
        kpdFact (if (> sheetArea 0.0) (* 100.0 (/ actualArea sheetArea)) 0.0)
        kpdBox (if (> sheetArea 0.0) (* 100.0 (/ bboxArea sheetArea)) 0.0))
  
  (princ (strcat "\nЛистов: " (itoa (length sheets)) " | деталей: " (itoa totalCnt)
                 " | полезный выход: " (cs-format-num kpdFact 1) "%"
                 " | габаритный выход: " (cs-format-num kpdBox 1) "%"))
  
  (if oversized
    (progn
      (princ (strcat "\nНЕРАЗМЕЩЕНО: " (itoa (length oversized)) " шт."))
      (foreach r oversized
        (princ (strcat "\n  " (cs-part-label r) " | " (nth 3 r))))))
  
  (pu-begin "CUTSHEET:xls")
  (if exportXls
    (if (not (cs-write-xls groups sheets oversized sheetW sheetH kerf))
      (progn
        (princ "\nXLS не создан — выполняется fallback CSV.")
        (cs-write-csv sheets oversized sheetW sheetH kerf))))
  (pu-end "CUTSHEET:xls")
  
  (if exportAcad
    (progn
      (setq insPt (getpoint "\nУкажите точку вставки карты раскроя: "))
      (if insPt
        (progn
          (cs-ensure-italic-style)
          (cs-ensure-bold-style)
          ;; П2.4а: кэш стилей - резолв заново на каждый прогон карты
          (setq *cs-style-cache* nil)
          (cs-setvar-transparency-display)
          (setq colorMap (cs-build-color-map groups))
          (setq doc (vl-catch-all-apply 'vla-get-ActiveDocument (list (vlax-get-acad-object))))
          (if (and (not (vl-catch-all-error-p doc)) doc)
            (progn (tu-undo-begin) (setq uMark T)))
          
          (setq lastEnt (entlast))

          ;; Ред. 25: набор для блока строится ТОЛЬКО из объектов, созданных
          ;; отрисовкой (обход базы затягивал чужие объекты и ронял упаковку).
          (setq *cs-created* '())
          (setq *cs-created-miss* 0)
          (princ "\n[CUTSHEET][STEP] отрисовка карты: старт")
          
          (pu-begin "CUTSHEET:draw-layout")
          (setq bbox1 (cs-draw-layout sheets sheetW sheetH insPt colorMap))
          (pu-end "CUTSHEET:draw-layout")
          (pu-begin "CUTSHEET:draw-summary")
          (setq bbox2 (cs-draw-summary groups sheets oversized sheetW sheetH rotateFlag
                    (list (+ (car (cadr bbox1)) *CUTSHEET-SUMMARY-GAP*) (cadr (cadr bbox1)))
                    kerf))
          (pu-end "CUTSHEET:draw-summary")
          
          ;; Собрать созданные примитивы для фактического bbox
          (setq ssNew (cs-ss-from-created))
          (tu-diag "DRAW" (strcat "примитивов карты: " (itoa (sslength ssNew))))
          
          ;; Этап 2: рамка - по ФАКТИЧЕСКИМ границам результата (GetBoundingBox
          ;; каждого примитива), не по расчетным координатам выноски.
          ;; Рамка = объединение фактических и расчетных границ:
          ;; не может зачеркнуть ни одну отрисованную строку.
          (pu-begin "CUTSHEET:bbox")
          (setq bboxFact (cs-entities-bbox ssNew))
          (pu-end "CUTSHEET:bbox")
          (setq bboxCalc (cs-combine-bbox bbox1 bbox2))
          (if bboxFact
            (setq bbox (cs-combine-bbox bboxFact bboxCalc))
            (progn
              (princ "\n[CUTSHEET][GUARD] фактический bbox недоступен - рамка по расчетным границам.")
              (setq bbox bboxCalc)))
          (setq bbox3 (cs-draw-frame bbox))
          (setq bbox (cs-combine-bbox bbox bbox3))
          
          ;; Пересобрать набор с учетом рамки для обертки в блок
          (setq ssNew (cs-ss-from-created))
          (princ (strcat "\n[CUTSHEET][STEP] отрисовка карты: готово (листы, сводка, рамка)"))
          (princ (strcat "\n[CUTSHEET][STEP] набор для блока: "
                         (itoa (sslength ssNew)) " объектов карты"
                         (if (> *cs-created-miss* 0)
                           (strcat ", НЕ отслежено: " (itoa *cs-created-miss*))
                           "")))
          (vl-catch-all-apply 'cs-scan-foreign-entities
                              (list lastEnt ssNew))
          (princ "\n[CUTSHEET][STEP] диагностика цепочки БД: завершена")

          
          (if (> (sslength ssNew) 0)
            (progn
              (princ "\nCUTSHEET: упаковка карты в блок...")
          (pu-begin "CUTSHEET:wrap-block")
              (setq baseName (vl-filename-base (getvar "DWGNAME"))
                    blockName
                      (cs-unique-block-name
                        (if (= (type ae-settings-expand-output-template) 'SUBR)
                          (ae-settings-expand-output-template 'CUTSHEET)
                          (strcat "Раскрой листа " baseName))))
              ;; Базовая точка блока = точка вставки = верхний левый угол рамки Невидимые
              (setq blockBasePt (list (car (car bbox3)) (cadr (cadr bbox3))))
              (cs-wrap-to-block blockName blockBasePt ssNew)
              (pu-end "CUTSHEET:wrap-block"))
  (tu-diag "BLOCK" (strcat "блок вставлен: " blockName)))
          
          (if uMark (progn (tu-undo-end doc) (setq uMark nil)))
          (cs-zoom-bbox bbox))
        (princ "\nКарта AutoCAD не построена."))))
  
  (princ))

;; ================= КОМАНДЫ =================
(defun c:CUTSHEET ( / uDoc r)
  ;; V13: «всё или ничего» - падение/отмена в середине откатывает всю карту
  (setq uDoc (tu-undo-begin))
  (setq r (vl-catch-all-apply 'cutsheet-main (list 'ASK)))
  (grtext -1 "") ;; П3: очистить прогресс (и при откате по ESC тоже)
  (if (vl-catch-all-error-p r)
    (progn
      (tu-undo-cancel uDoc)
      (princ (strcat "\n[CUTSHEET] Операция прервана и откачена: "
                     (vl-catch-all-error-message r))))
    (tu-undo-end uDoc))
  (princ))
(defun c:РАСКРОЙЛИСТА () (c:CUTSHEET))

;; CUTSHEET.LSP загружен (ред. 38: в отчётах «Тип» — состояние видимости блока, марка отдельно; марка в XLS и CSV; сводка — строка на каждую марку; подписи детали не наползают; марки в перечне изделий; блоки заполнения — размер в свету + припуск; марка элемента в углу детали; заголовок «Выбранные слои» со счётчиком; карта в блок берёт только свои объекты; скан и состав блока с защитой; фильтры слоёв; U2, П1-П3, V5). Команды: CUTSHEET, РАСКРОЙЛИСТА
(if (member (ae-reload-sym-type 'ae-banner-add) '(SUBR USUBR))
  (ae-banner-add "CUTSHEET" '(
      ("CUTSHEET / РАСКРОЙЛИСТА" "раскрой листа: отчёты и марки" "38"))))
(princ)
