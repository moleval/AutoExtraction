;;; ============================================================
;;; CUTLINE.LSP — модуль линейного раскроя мерного материала
;;; Команда: CUTLINE / РАСКРОЙХЛЫСТА
;;; Объекты: LINE, MLINE, динамические блоки (длина — по маскам
;;; свойства из настроек задачи: task.CUTLINE / input.block.length)
;;; Алгоритм: First-Fit Decreasing (FFD)
;;;
;;; ЗАЛИВКА ДЕТАЛЕЙ:
;;;   - SOLID + ActiveX EntityTransparency (0..90%)
;;;   - TRANSPARENCYDISPLAY включается автоматически
;;;
;;; ШАПКА КАРТЫ РАСКРОЯ:
;;;   - заголовок, подзаголовок, линейка с метками 0 и stock
;;;   - рисуется над первым хлыстом
;;; ============================================================
(vl-load-com)

;; ================= Константы =================
(setq *CUTLINE-MIN-LENGTH*   100.0)
(setq *CUTLINE-MAX-LENGTH* 500000.0)
(setq *CUTLINE-DEFAULT-TOL*    1.0)
(setq *CUTLINE-DEFAULT-STOCK* 6000.0)
(setq *CUTLINE-DEFAULT-KERF*   0.0)

;; ЗАЛИВКА: прозрачность 0.0..1.0 (где 1.0 = 90% прозрачности)
(setq *CUTLINE-PART-TRANSPARENCY* 0.70)
(setq *CUTLINE-WASTE-TRANSPARENCY* 0.3)

(setq *NEST-PALETTE* '(1 2 3 4 5 6 30 210 140 90))
(setq *NEST-STYLE-NAME* "Раскрой Italic")
(setq *NEST-ITALIC-ANGLE* 0.26)
(setq *NEST-TEXT-STYLE* nil)
;; Жирный стиль текста
(setq *NEST-BOLD-STYLE-NAME* "Основной стиль (надписи без наклона)")
(setq *NEST-BOLD-TEXT-STYLE* nil)
(setq *NEST-COLOR-OUTLINE* 7)
(setq *NEST-COLOR-LABEL*   7)
(setq *NEST-COLOR-WASTE*   8)
(setq *NEST-COLOR-TITLE*   5)
(setq *NEST-COLOR-HEADER*  3)
(setq *NEST-COLOR-VALUE*   7)
(setq *NEST-COLOR-KPD*     1)
;; Цвет текста длины детали (желтый)
(setq *NEST-COLOR-PART-TEXT* 2)
;; Марка элемента (атрибут МАРКА динамического блока) в углу детали
(setq *CUTLINE-MARK-COLOR* 7)

;; ================= ПАРАМЕТРЫ ШАПКИ КАРТЫ РАСКРОЯ =================
(setq *CUTLINE-ROW-H*          200.0)   ;; высота строки шапки
(setq *CUTLINE-TEXT-H*          75.0)   ;; высота подзаголовка и меток
(setq *CUTLINE-TITLE-H*        100.0)   ;; высота заголовка
(setq *CUTLINE-OUTLINE-COLOR*     7)    ;; цвет линейки
(setq *CUTLINE-TITLE-COLOR*       5)    ;; цвет заголовка
(setq *CUTLINE-HEADER-COLOR*      3)    ;; цвет подзаголовка
(setq *CUTLINE-VALUE-COLOR*       7)    ;; цвет меток линейки
;; ====================================================================

;; ================= РАМКА ВОКРУГ КАРТЫ РАСКРОЯ =================
(setq *CUTLINE-FRAME-LAYER*       "Невидимые")   ;; слой рамки
(setq *CUTLINE-FRAME-PAD-LEFT*     300.0)        ;; отступ слева (мм)
(setq *CUTLINE-FRAME-PAD-RIGHT*    125.0)        ;; отступ справа
(setq *CUTLINE-FRAME-PAD-TOP*      125.0)        ;; отступ сверху
(setq *CUTLINE-FRAME-PAD-BOTTOM*   200.0)        ;; отступ снизу
;; =================================================================

(if (not (boundp '*n1-tmp-choice*))
  (setq *n1-tmp-choice* 'ALL))

(if (not (boundp '*n1-tmp-stock*))   (setq *n1-tmp-stock* *CUTLINE-DEFAULT-STOCK*))
(if (not (boundp '*n1-tmp-kerf*))    (setq *n1-tmp-kerf*  *CUTLINE-DEFAULT-KERF*))
(if (not (boundp '*n1-tmp-chk-xls*)) (setq *n1-tmp-chk-xls* T))
(if (not (boundp '*n1-tmp-chk-acad*)) (setq *n1-tmp-chk-acad* T))

(if (not (boundp '*n1-tmp-dynblock-type*))
  (setq *n1-tmp-dynblock-type* "")
)

(if (not (boundp '*n1-dynblock-types-list*))
  (setq *n1-dynblock-types-list* '())
)

(if (not (boundp '*n1-tmp-mline-type*))
  (setq *n1-tmp-mline-type* "")
)

(if (not (boundp '*n1-mline-types-list*))
  (setq *n1-mline-types-list* '())
)

(if (not (boundp '*n1-cutline-ss*))
  (setq *n1-cutline-ss* nil)
)

(if (not (boundp '*CUTLINE-LAST-STOCK*)) (setq *CUTLINE-LAST-STOCK* *CUTLINE-DEFAULT-STOCK*))
(if (not (boundp '*CUTLINE-LAST-KERF*))  (setq *CUTLINE-LAST-KERF*  *CUTLINE-DEFAULT-KERF*))
(if (not (boundp '*CUTLINE-LAST-XLS*))   (setq *CUTLINE-LAST-XLS*   T))
(if (not (boundp '*CUTLINE-LAST-ACAD*))  (setq *CUTLINE-LAST-ACAD*  T))

;; ---------- Утилиты ----------
;; Этап 2 (V5): лимит количества деталей - защита от зависания
;; при ошибочной выборке (x100 объектов). Именованный, изменяемый.
;; V5 (уточнение 2026-09-23): превышение = alert (GUI) + GUARD в командную
;; строку + запрос на продолжение; Нет/Enter останавливает (как раньше).
(setq *n1-max-parts* 10000)

;; Этап 2 (V6): страж итераций FFD - верхняя граница числа попыток размещения.
(setq *n1-max-placement-attempts* 1000000)

(defun n1-split-string (str delim / pos result item)
  (setq result '())
  (while (setq pos (vl-string-search delim str))
    (setq item (vl-string-trim " " (substr str 1 pos)))
    (setq result (cons item result))
    (setq str (substr str (+ pos 2)))
  )
  (setq item (vl-string-trim " " str))
  (if (> (strlen item) 0)
    (setq result (cons item result))
  )
  (reverse result)
)

(defun n1-ensure-italic-style ( / result)
  (if (tblsearch "STYLE" *NEST-STYLE-NAME*)
    (progn
      (setq *NEST-TEXT-STYLE* *NEST-STYLE-NAME*)
    )
    (progn
      (setq result
        (entmake (list (cons 0 "STYLE") (cons 2 *NEST-STYLE-NAME*)
                       (cons 70 0) (cons 40 0.0) (cons 41 1.0)
                       (cons 50 *NEST-ITALIC-ANGLE*) (cons 71 0)
                       (cons 42 2.5) (cons 3 "Arial") (cons 4 ""))))
      (if (and result (tblsearch "STYLE" *NEST-STYLE-NAME*))
        (setq *NEST-TEXT-STYLE* *NEST-STYLE-NAME*)
        (setq *NEST-TEXT-STYLE* nil)
      )
    )
  )
)

;; ============================================================
;; СОЗДАНИЕ ЖИРНОГО СТИЛЯ ТЕКСТА
;; "Основной стиль (надписи без наклона)" со шрифтом arialbd.ttf
;; ============================================================
(defun n1-ensure-bold-style ( / result)
  (if (tblsearch "STYLE" *NEST-BOLD-STYLE-NAME*)
    (setq *NEST-BOLD-TEXT-STYLE* *NEST-BOLD-STYLE-NAME*)
    (progn
      (setq result
        (entmake
          (list '(0 . "STYLE")
                '(100 . "AcDbSymbolTableRecord")
                '(100 . "AcDbTextStyleTableRecord")
                (cons 2 *NEST-BOLD-STYLE-NAME*)
                '(70 . 0)
                '(40 . 0.0)
                '(41 . 1.0)
                '(50 . 0.0)
                '(71 . 0)
                '(42 . 2.5)
                '(3 . "arialbd.ttf")
                '(4 . ""))))
      (if (and result (tblsearch "STYLE" *NEST-BOLD-STYLE-NAME*))
        (setq *NEST-BOLD-TEXT-STYLE* *NEST-BOLD-STYLE-NAME*)
        (setq *NEST-BOLD-TEXT-STYLE* nil)
      )
    )
  )
)

(defun n1-unique-block-name (base)
  ;; U3: единый генератор - см. common/task-utils.lsp
  (tu-unique-block-name base))

(defun n1-block-insert (name insPt / ent)
  (entmake (list (cons 0 "INSERT") (cons 100 "AcDbEntity")
                 (cons 100 "AcDbBlockReference") (cons 2 name)
                 (cons 10 (list (car insPt) (cadr insPt) 0.0))
                 (cons 41 1.0) (cons 42 1.0) (cons 43 1.0) (cons 50 0.0)))
  (setq ent (entlast))
  (if (= (type ae-settings-output-layer) 'SUBR)
    (ae-settings-apply-entity-layer ent
      (ae-settings-output-layer 'CUTLINE)))
  ent
)

;; ============================================================
;; ЗАЩИТА УПАКОВКИ РАСКЛАДКИ В БЛОК (ред. 15)
;; Если в чертеже есть выделенные (grip) объекты, команда -BLOCK
;; добавляет их к переданному набору: посторонние объекты уходят
;; внутрь блока и пропадают из чертежа. Перед -BLOCK предвыделение
;; снимается, а PICKFIRST на время команды выключается.
;; ============================================================

;; Сколько объектов сейчас выделено (grip). 0 — предвыделения нет.
(defun n1-pickfirst-count ( / pf)
  (setq pf (ssgetfirst))
  (if (and pf (cadr pf)) (sslength (cadr pf)) 0)
)

;; Снять предвыделение. quiet=T — без сообщения.
;; Возвращает число снятых объектов (0 — снимать было нечего).
(defun n1-clear-pickfirst (quiet / n)
  (setq n (n1-pickfirst-count))
  (sssetfirst nil nil)
  (if (and (> n 0) (not quiet))
    (princ (strcat "\n[CUTLINE] Снято предвыделение: " (itoa n)
                   " объект(ов) — в блок раскладки они не попадут."))
  )
  n
)

;; Ключ типа объекта: DXF-код 0 и ActiveX ObjectName -> один словарь
(defun n1-type-key (typ / s)
  (setq s (strcase (if (= (type typ) 'STR) typ "")))
  (cond
    ((= s "ACDBLINE")          "LINE")
    ((= s "ACDBPOLYLINE")      "LWPOLYLINE")
    ((= s "ACDBTEXT")          "TEXT")
    ((= s "ACDBMTEXT")         "MTEXT")
    ((= s "ACDBTRACE")         "SOLID")
    ((= s "ACDBSOLID")         "SOLID")
    ((= s "ACDBMLINE")         "MLINE")
    ((= s "ACDBBLOCKREFERENCE") "INSERT")
    (T s)
  )
)

;; Состав набора: список пар (ТИП . КОЛИЧЕСТВО)
(defun n1-ss-type-tally (ss / i ent typ rec out)
  (setq out '() i 0)
  (if ss
    (repeat (sslength ss)
      (setq ent (ssname ss i))
      (setq typ (n1-type-key (cdr (assoc 0 (entget ent)))))
      (setq rec (assoc typ out))
      (if rec
        (setq out (subst (cons typ (1+ (cdr rec))) rec out))
        (setq out (append out (list (cons typ 1))))
      )
      (setq i (1+ i))
    )
  )
  out
)

;; Тип объекта внутри блока: тем же способом, что и у набора раскладки
;; (DXF-код 0 через ename); ObjectName — только запасной путь.
(defun n1-object-type-key (obj / e typ)
  (setq typ nil)
  (setq e (vl-catch-all-apply 'vlax-vla-object->ename (list obj)))
  (if (not (vl-catch-all-error-p e))
    (setq typ (n1-type-key (cdr (assoc 0 (entget e)))))
  )
  (if (or (null typ) (= typ ""))
    (setq typ (n1-type-key (vl-catch-all-apply 'vla-get-ObjectName (list obj))))
  )
  (if (or (null typ) (= typ "")) "?" typ)
)

;; Состав определения блока (ActiveX-обход): (ВСЕГО ТИП . КОЛИЧЕСТВО ...)
(defun n1-block-type-tally (blockName / acad doc blocks blk obj n out typ rec)
  (setq acad (vl-catch-all-apply 'vlax-get-acad-object '()))
  (if (vl-catch-all-error-p acad)
    nil
    (progn
      (setq doc (vl-catch-all-apply 'vla-get-ActiveDocument (list acad)))
      (if (vl-catch-all-error-p doc)
        nil
        (progn
          (setq blocks (vl-catch-all-apply 'vla-get-Blocks (list doc)))
          (setq blk
            (if (vl-catch-all-error-p blocks)
              nil
              (vl-catch-all-apply 'vla-Item (list blocks blockName))))
          (if (vl-catch-all-error-p blk)
            nil
            (progn
              (setq n 0 out '())
              (vlax-for obj blk
                (setq n (1+ n))
                (setq typ (n1-object-type-key obj))
                (setq rec (assoc typ out))
                (if rec
                  (setq out (subst (cons typ (1+ (cdr rec))) rec out))
                  (setq out (append out (list (cons typ 1))))
                )
              )
              (cons n out)
            )
          )
        )
      )
    )
  )
)

;; Состав одной строкой: "LINE 12, LWPOLYLINE 40, TEXT 33"
(defun n1-tally-str (tally / s rec)
  (setq s "")
  (foreach rec tally
    (setq s (strcat s (if (= s "") "" ", ")
                    (car rec) " " (itoa (cdr rec)))))
  s
)

(defun n1-tally-sort (tally)
  (vl-sort (mapcar '(lambda (x) (cons (car x) (cdr x))) tally)
    '(lambda (a b) (< (car a) (car b))))
)

;; Совпадают ли составы (порядок не важен)
(defun n1-tally-equal-p (a b)
  (equal (n1-tally-sort a) (n1-tally-sort b))
)

;; ============================================================
;; УЧЁТ ОБЪЕКТОВ РАСКЛАДКИ (ред. 16)
;; Набор для упаковки в блок — ТОЛЬКО объекты, созданные отрисовкой.
;; Обход базы (entnext) для этого не годится: он затягивает посторонние
;; объекты чертежа (атрибуты и вставки из других пространств/определений),
;; а -BLOCK вместе с атрибутами уносит в блок и их вставку-владельца.
;; ============================================================

(if (not (boundp '*n1-created*))
  (setq *n1-created* nil)
)

;; Сколько объектов не удалось отследить (диагностика)
(if (not (boundp '*n1-created-miss*))
  (setq *n1-created-miss* 0)
)

;; Всё, что печатается, приводится к строке: диагностика не имеет права
;; упасть на чужом типе (например, на имени объекта вместо имени).
(defun n1-safe-str (x)
  (if (= (type x) 'STR) x (vl-princ-to-string x))
)

;; Имя владельца объекта: слой/пространство/определение блока.
;; Код 330 возвращает то handle-строку, то имя объекта (зависит от контекста),
;; поэтому обрабатываются оба случая. Только чтение, все вызовы под защитой:
;; диагностика НЕ имеет права упасть и уронить раскрой.
(defun n1-owner-name (ent / d h oe od name)
  (setq name nil)
  (setq d (vl-catch-all-apply (function entget) (list ent)))
  (if (not (vl-catch-all-error-p d))
    (progn
      (setq h (cdr (assoc 330 d)))
      (cond
        ;; Владелец уже пришёл именем объекта
        ((= (type h) 'ENAME) (setq oe h))
        ;; Владелец пришёл handle-строкой
        ((= (type h) 'STR)
         (setq oe (vl-catch-all-apply (function handent) (list h)))
         (if (vl-catch-all-error-p oe) (setq oe nil)))
      )
      (if oe
        (progn
          (setq od (vl-catch-all-apply (function entget) (list oe)))
          (if (not (vl-catch-all-error-p od))
            (setq name (cdr (assoc 2 od)))
          )
        )
      )
    )
  )
  (cond
    ((= (type name) 'STR) name)
    ((= (type h) 'ENAME)
     (strcat "имя объекта " (n1-safe-str h)))
    ((= (type h) 'STR) (strcat "handle " h))
    (T "?")
  )
)

;; Создать объект и запомнить его в *n1-created*.
;; Тип проверяется: entlast обязан вернуть именно созданный объект.
(defun n1-mk (dxf / want before res e)
  (setq want (n1-type-key (cdr (assoc 0 dxf))))
  (setq before (entlast))
  (setq res (entmake dxf))
  (if res
    (progn
      (setq e (entlast))
      (if (and e (not (eq e before))
               (= (n1-type-key (cdr (assoc 0 (entget e)))) want))
        (setq *n1-created* (cons e *n1-created*))
        (setq *n1-created-miss* (1+ *n1-created-miss*))
      )
    )
  )
  res
)

;; Диагностика: что обход базы затянул бы в блок помимо раскладки.
;; Работает только на чтение и НИКОГДА не возвращает ошибку наружу: при сбое
;; печатается причина, раскрой продолжается (диагностика не роняет работу).
(defun n1-scan-foreign-entities (from-ent ssNew / ent n typ layer owner res)
  (setq n 0)
  (setq ent (vl-catch-all-apply (function entnext)
              (if from-ent (list from-ent) '())))
  (while (and ent (not (vl-catch-all-error-p ent)))
    (if (not (n1-ss-contains-p ssNew ent))
      (progn
        (setq typ   (n1-safe-str
                      (n1-type-key (cdr (assoc 0 (entget ent))))))
        (setq layer (n1-safe-str (cdr (assoc 8 (entget ent)))))
        (setq owner (vl-catch-all-apply (function n1-owner-name) (list ent)))
        (if (vl-catch-all-error-p owner)
          (setq owner (strcat "ошибка определения: "
                              (n1-safe-str
                                (vl-catch-all-error-message owner)))))
        (setq n (1+ n))
        (if (<= n 10)
          (princ (strcat "\n[CUTLINE][SCAN] посторонний объект в цепочке БД: "
                         typ " (слой " layer ", владелец " owner ")")))
      )
    )
    (setq ent (vl-catch-all-apply (function entnext) (list ent)))
  )
  (if (and ent (vl-catch-all-error-p ent))
    (princ (strcat "\n[CUTLINE][SCAN] Обход прерван: "
                   (n1-safe-str (vl-catch-all-error-message ent)))))
  (if (> n 0)
    (princ (strcat "\n[CUTLINE][SCAN] Посторонних объектов в цепочке БД: "
                   (itoa n) " — в блок раскладки не берутся."))
    (princ "\n[CUTLINE][SCAN] Посторонних объектов в цепочке БД нет."))
  n
)

;; Собственная undo-метка вокруг отрисовки и упаковки раскладки.
;; Нужна для детерминированного отката: сравнивать DBMOD нельзя (в уже
;; несохранённом чертеже он не меняется), а откатывать нужно ровно группу
;; раскладки (UNDO Back после EndUndoMark).
(defun n1-wrap-mark-begin (doc)
  (if (and doc (not (vl-catch-all-error-p doc))
           (not (vl-catch-all-error-p
                  (vl-catch-all-apply 'vla-StartUndoMark (list doc)))))
    T
    nil
  )
)

(defun n1-wrap-mark-end (doc ok / old-echo)
  (if (and doc (not (vl-catch-all-error-p doc)))
    (progn
      (vl-catch-all-apply 'vla-EndUndoMark (list doc))
      (if (not ok)
        (progn
          (setq old-echo (getvar "CMDECHO"))
          (vl-catch-all-apply 'setvar (list "CMDECHO" 0))
          (princ "\n[CUTLINE] Откат раскладки (UNDO Back)...")
          (vl-catch-all-apply 'vl-cmdf (list "_.UNDO" "1"))
          (vl-catch-all-apply 'setvar (list "CMDECHO" old-echo))
        )
      )
    )
  )
)

(defun n1-ss-contains-p (ss ent / i found)
  (setq i 0 found nil)
  (if ss
    (repeat (sslength ss)
      (if (equal (ssname ss i) ent) (setq found T))
      (setq i (1+ i))
    )
  )
  found
)

(defun n1-apply-new-block-ref-layers (before after layer / i ent)
  (if (and after layer)
    (progn
      (setq i 0)
      (repeat (sslength after)
        (setq ent (ssname after i))
        (if (not (n1-ss-contains-p before ent))
          (ae-settings-apply-entity-layer ent layer))
        (setq i (1+ i))
      )
    )
  )
)

(defun n1-build-color-map (pieces / palette i map rec)
  (setq palette *NEST-PALETTE* i 0 map '())
  (foreach rec pieces
    (setq map (cons (cons (car rec) (nth (rem i (length palette)) palette)) map))
    (setq i (1+ i))
  )
  (reverse map)
)

(defun n1-get-color (color-map len / pair)
  (setq pair (assoc len color-map))
  (if pair (cdr pair) 7)
)

(defun n1-draw-text (pt h str color / style c)
  (setq style (if (and *NEST-TEXT-STYLE* (/= *NEST-TEXT-STYLE* ""))
                *NEST-TEXT-STYLE* (getvar "TEXTSTYLE")))
  (setq c (if (and color (numberp color)) color 7))
  (n1-mk (list (cons 0 "TEXT") (cons 62 c) (cons 7 style)
                 (cons 10 (list (car pt) (cadr pt) 0.0))
                 (cons 40 h) (cons 1 str) (cons 50 0.0)))
)

;; ============================================================
;; ЖИРНЫЙ ТЕКСТ С ПОВОРОТОМ
;; angle: угол поворота в ГРАДУСАХ (конвертируется в радианы)
;; ============================================================
(defun n1-draw-text-bold (pt h str color angle / c style angle-rad)
  (setq c (if (and color (numberp color)) color 7))
  (n1-ensure-bold-style)
  (setq style (if (and *NEST-BOLD-TEXT-STYLE* (/= *NEST-BOLD-TEXT-STYLE* ""))
                *NEST-BOLD-TEXT-STYLE* (getvar "TEXTSTYLE")))
  (setq angle-rad (if (and angle (numberp angle)) (* angle (/ pi 180.0)) 0.0))
  (n1-mk (list (cons 0 "TEXT") (cons 62 c) (cons 7 style)
                 (cons 10 (list (car pt) (cadr pt) 0.0))
                 (cons 40 h) (cons 1 str) (cons 50 angle-rad)))
)

;; ============================================================
;; ЖИРНЫЙ ТЕКСТ С ПОВОРОТОМ И ЦЕНТРИРОВАНИЕМ
;; Текст центрируется относительно точки вставки (коды 72=1, 73=2, 11)
;; ============================================================
(defun n1-draw-text-bold-center (pt h str color angle / c style angle-rad)
  (setq c (if (and color (numberp color)) color 7))
  (n1-ensure-bold-style)
  (setq style (if (and *NEST-BOLD-TEXT-STYLE* (/= *NEST-BOLD-TEXT-STYLE* ""))
                *NEST-BOLD-TEXT-STYLE* (getvar "TEXTSTYLE")))
  (setq angle-rad (if (and angle (numberp angle)) (* angle (/ pi 180.0)) 0.0))
  (n1-mk (list (cons 0 "TEXT") (cons 62 c) (cons 7 style)
                 (cons 10 (list (car pt) (cadr pt) 0.0))
                 (cons 11 (list (car pt) (cadr pt) 0.0))
                 (cons 40 h) (cons 1 str) (cons 50 angle-rad)
                 (cons 72 1)
                 (cons 73 2)))
)

;; ============================================================
;; ТЕКСТ С ВЫРАВНИВАНИЕМ ПО ПРАВОМУ КРАЮ И ВЕРТИКАЛЬНОЙ СЕРЕДИНЕ
;; Используется для меток хлыста слева (не наезжают на хлыст)
;; ============================================================
(defun n1-draw-text-right (pt h str color / c style)
  (setq c (if (and color (numberp color)) color 7))
  (setq style (if (and *NEST-TEXT-STYLE* (/= *NEST-TEXT-STYLE* ""))
                *NEST-TEXT-STYLE* (getvar "TEXTSTYLE")))
  (n1-mk (list (cons 0 "TEXT") (cons 62 c) (cons 7 style)
                 (cons 10 (list (car pt) (cadr pt) 0.0))
                 (cons 11 (list (car pt) (cadr pt) 0.0))
                 (cons 40 h) (cons 1 str) (cons 50 0.0)
                 (cons 72 2)    ;; горизонтальное: по правому краю
                 (cons 73 2)))  ;; вертикальное: середина
)

;; ============================================================
;; ЖИРНЫЙ ТЕКСТ С ВЫРАВНИВАНИЕМ ПО ПРАВОМУ КРАЮ И ВЕРТИКАЛЬНОЙ СЕРЕДИНЕ
;; Стиль Arial Bold, используется для меток шапки слева
;; ============================================================
(defun n1-draw-text-bold-right (pt h str color angle / c style angle-rad)
  (setq c (if (and color (numberp color)) color 7))
  (n1-ensure-bold-style)
  (setq style (if (and *NEST-BOLD-TEXT-STYLE* (/= *NEST-BOLD-TEXT-STYLE* ""))
                *NEST-BOLD-TEXT-STYLE* (getvar "TEXTSTYLE")))
  (setq angle-rad (if (and angle (numberp angle)) (* angle (/ pi 180.0)) 0.0))
  (n1-mk (list (cons 0 "TEXT") (cons 62 c) (cons 7 style)
                 (cons 10 (list (car pt) (cadr pt) 0.0))
                 (cons 11 (list (car pt) (cadr pt) 0.0))
                 (cons 40 h) (cons 1 str) (cons 50 angle-rad)
                 (cons 72 2)    ;; горизонтальное: по правому краю
                 (cons 73 2)))  ;; вертикальное: середина
)

;; ============================================================
;; ЖИРНЫЙ ТЕКСТ С ВЫРАВНИВАНИЕМ ПО ЛЕВОМУ КРАЮ И ВЕРТИКАЛЬНОЙ СЕРЕДИНЕ
;; Стиль Arial Bold. Зеркально n1-draw-text-bold-right.
;; Используется для меток справа (правее хлыста / линейки).
;; ============================================================
(defun n1-draw-text-bold-left (pt h str color angle / c style angle-rad)
  (setq c (if (and color (numberp color)) color 7))
  (n1-ensure-bold-style)
  (setq style (if (and *NEST-BOLD-TEXT-STYLE* (/= *NEST-BOLD-TEXT-STYLE* ""))
                *NEST-BOLD-TEXT-STYLE* (getvar "TEXTSTYLE")))
  (setq angle-rad (if (and angle (numberp angle)) (* angle (/ pi 180.0)) 0.0))
  (n1-mk (list (cons 0 "TEXT") (cons 62 c) (cons 7 style)
                 (cons 10 (list (car pt) (cadr pt) 0.0))
                 (cons 11 (list (car pt) (cadr pt) 0.0))
                 (cons 40 h) (cons 1 str) (cons 50 angle-rad)
                 (cons 72 0)    ;; горизонтальное: по левому краю
                 (cons 73 2)))  ;; вертикальное: середина
)

;; ============================================================
;; ДВОЙНАЯ ВЕРТИКАЛЬНАЯ ЛИНИЯ РЕЗА
;; Рисует две параллельные линии со сдвигом ±offset
;; ============================================================

(defun n1-draw-line (p1 p2 color)
  (n1-mk (list (cons 0 "LINE") (cons 62 color)
                 (cons 10 (list (car p1) (cadr p1) 0.0))
                 (cons 11 (list (car p2) (cadr p2) 0.0))))
)

(defun n1-draw-rect (p1 p2 color / x1 y1 x2 y2)
  (setq x1 (car p1) y1 (cadr p1) x2 (car p2) y2 (cadr p2))
  (n1-mk (list (cons 0 "LWPOLYLINE") (cons 100 "AcDbEntity")
                 (cons 62 color) (cons 100 "AcDbPolyline")
                 (cons 90 4) (cons 70 1)
                 (cons 10 (list x1 y1)) (cons 10 (list x2 y1))
                 (cons 10 (list x2 y2)) (cons 10 (list x1 y2))))
)

;; ============================================================
;; ЗАЛИВКА С ПРОЗРАЧНОСТЬЮ
;; SOLID + ActiveX EntityTransparency (0..90)
;; ============================================================

(defun n1-apply-transparency (ent val90 / obj r)
  (if ent
    (progn
      (setq obj (vl-catch-all-apply 'vlax-ename->vla-object (list ent)))
      (if (not (vl-catch-all-error-p obj))
        (progn
          (setq r (vl-catch-all-apply 'vlax-put-property
                    (list obj 'EntityTransparency val90)))
          (if (vl-catch-all-error-p r)
            (vl-catch-all-apply 'vlax-put-property
              (list obj 'Transparency val90)))
        )
      )
    )
  )
  ent
)

(defun n1-draw-filled-rect (p1 p2 color transparency / x1 y1 x2 y2 ent res aci)
  (setq x1 (car p1) y1 (cadr p1) x2 (car p2) y2 (cadr p2))
  (setq aci (fix (+ 0.5 (* transparency 90.0))))
  (if (> aci 90) (setq aci 90))
  (if (< aci 0) (setq aci 0))

  (setq res
    (n1-mk
      (list
        (cons 0 "SOLID")
        (cons 100 "AcDbEntity")
        (cons 100 "AcDbTrace")
        (cons 10 (list x1 y1 0.0))
        (cons 11 (list x2 y1 0.0))
        (cons 12 (list x1 y2 0.0))
        (cons 13 (list x2 y2 0.0))
        (cons 62 color)
        (cons 39 0.0)
      )
    )
  )

  (if res
    (progn
      (setq ent (entlast))
      (n1-apply-transparency ent aci)
      ent
    )
    nil
  )
)

(defun n1-enable-transparency-display ( / )
  (vl-catch-all-apply 'setvar (list "TRANSPARENCYDISPLAY" 1))
)

(defun n1-disable-transparency-display (old-val / )
  (if (and old-val (numberp old-val))
    (vl-catch-all-apply 'setvar (list "TRANSPARENCYDISPLAY" old-val))
  )
)

;; ============================================================
;; СОЗДАНИЕ СЛОЯ РАМКИ (если не существует)
;; ============================================================
(defun n1-ensure-frame-layer ( / )
  (if (not (tblsearch "LAYER" *CUTLINE-FRAME-LAYER*))
    (entmake
      (list '(0 . "LAYER")
            '(100 . "AcDbSymbolTableRecord")
            '(100 . "AcDbLayerTableRecord")
            (cons 2 *CUTLINE-FRAME-LAYER*)
            '(70 . 0)
            '(62 . 7)
            '(6 . "Continuous")
            '(370 . -3)))
  )
)

;; ============================================================
;; РАМКА ВОКРУГ КАРТЫ РАСКРОЯ (LWPOLYLINE на слое *CUTLINE-FRAME-LAYER*)
;; bbox: ((x1 y1) (x2 y2)) — границы шапки+хлыстов
;; Отступы задаются константами *CUTLINE-FRAME-PAD-*
;; Возвращает bbox рамки (с учетом отступов)
;; ============================================================
(defun n1-draw-frame (bbox / x1 y1 x2 y2)
  (n1-ensure-frame-layer)
  (setq x1 (- (car  (car  bbox)) *CUTLINE-FRAME-PAD-LEFT*))
  (setq y1 (- (cadr (car  bbox)) *CUTLINE-FRAME-PAD-BOTTOM*))
  (setq x2 (+ (car  (cadr bbox)) *CUTLINE-FRAME-PAD-RIGHT*))
  (setq y2 (+ (cadr (cadr bbox)) *CUTLINE-FRAME-PAD-TOP*))
  (n1-mk
    (list '(0 . "LWPOLYLINE")
          '(100 . "AcDbEntity")
          (cons 8 *CUTLINE-FRAME-LAYER*)
          '(100 . "AcDbPolyline")
          '(90 . 4)
          '(70 . 1)
          (cons 10 (list x1 y1))
          (cons 10 (list x2 y1))
          (cons 10 (list x2 y2))
          (cons 10 (list x1 y2))))
  (list (list x1 y1) (list x2 y2))
)

;; ============================================================
;; ШАПКА КАРТЫ РАСКРОЯ
;; - заголовок "КАРТА РАСКРОЯ ХЛЫСТОВ" (жирный);
;; - подзаголовок "Заготовка: X мм || Пропил: Y мм" (шрифт как у "Хлыст N");
;; - линейка с одинарными засечками;
;; - метки 0 (справа-налево) и stock (слева-направо) — зеркально.
;; ============================================================
(defun n1-draw-header (insPt stock kerf / x0 y0 rowH txtH titleH barHeight
                       labelX labelX-right tick-half tick-base layout-txtH)
  (setq x0        (car insPt)
        y0        (cadr insPt)
        rowH      *CUTLINE-ROW-H*
        txtH      *CUTLINE-TEXT-H*
        titleH    *CUTLINE-TITLE-H*
        barHeight (/ stock 45.0))

  ;; Высота шрифта как у метки "Хлыст N" в n1-draw-layout
  (setq layout-txtH (* (/ stock 30.0) 0.30))

  ;; Позиции меток (отступ = barHeight * 0.6, как у "Хлыст 1")
  (setq labelX       (- x0 (* barHeight 0.6)))
  (setq labelX-right (+ x0 stock (* barHeight 0.6)))

  ;; Параметры одинарных засечек (небольшой размер)
  (setq tick-half (* rowH 0.12))
  (setq tick-base (+ y0 (* rowH 2.0)))

  ;; 1. Заголовок (жирный)
  (n1-draw-text-bold
    (list x0 (+ y0 (* rowH 3.4)))
    titleH
    "КАРТА РАСКРОЯ ХЛЫСТОВ"
    *CUTLINE-TITLE-COLOR* 0.0)

  ;; 2. Подзаголовок с || — высота шрифта как у "Хлыст N"
  (n1-draw-text
    (list x0 (+ y0 (* rowH 2.7)))
    layout-txtH
    (strcat "Заготовка: " (rtos stock 2 0)
            " мм   ||   Пропил: " (rtos kerf 2 1) " мм")
    *CUTLINE-HEADER-COLOR*)

  ;; 3. Линейка
  (n1-draw-line
    (list x0 tick-base)
    (list (+ x0 stock) tick-base)
    *CUTLINE-OUTLINE-COLOR*)

  ;; 4. Одинарные вертикальные засечки
  (n1-draw-line (list x0 (- tick-base tick-half))
                (list x0 (+ tick-base tick-half))
                *CUTLINE-OUTLINE-COLOR*)
  (n1-draw-line (list (+ x0 stock) (- tick-base tick-half))
                (list (+ x0 stock) (+ tick-base tick-half))
                *CUTLINE-OUTLINE-COLOR*)

  ;; 5. Левая метка "0" — выровнена по правому краю
  (n1-draw-text-bold-right
    (list labelX tick-base)
    (* layout-txtH 1.1)
    "0"
    *CUTLINE-VALUE-COLOR* 0.0)

  ;; 6. Правая метка stock — ПРАВЕЕ линейки, выровнена по левому краю
  ;;    (зеркально метке "0", та же высота шрифта)
  (n1-draw-text-bold-left
    (list labelX-right tick-base)
    (* layout-txtH 1.1)
    (rtos stock 2 0)
    *CUTLINE-VALUE-COLOR* 0.0)

  ;; BBox шапки (расширен вправо для метки stock)
  (list
    (list (- x0 (* barHeight 2.0)) (+ y0 (* rowH 2.0)))
    (list (+ x0 stock (* barHeight 2.0)) (+ y0 (* rowH 3.9))))
)

;; ============================================================

(defun n1-expand (pieces / sorted-groups out rec len cnt i)
  (setq sorted-groups (vl-sort pieces '(lambda (a b) (> (car a) (car b)))))
  (setq out '())
  (foreach rec sorted-groups
    (setq len (car rec) cnt (fix (cadr rec)) i 0)
    (while (< i cnt)
      (setq out (cons len out))
      (setq i (1+ i))
    )
  )
  (reverse out)
)

(defun n1-replace-nth (lst idx new / i out)
  (setq i 0 out '())
  (foreach x lst
    (if (= i idx)
      (setq out (cons new out))
      (setq out (cons x out))
    )
    (setq i (1+ i))
  )
  (reverse out)
)

;; ============================================================
;; Алгоритм раскроя FFD
;; ============================================================
(defun n1-ffd (sorted-pieces stock kerf / bars p placed j bar newbar skip attempts stopGuard)
  ;; V6: страж итераций - считает попытки размещения; при превышении лимита
  ;; остаток деталей уходит в пропущенные (честный частичный результат).
  (setq bars '())
  (setq skip 0)
  (setq attempts 0)
  (setq stopGuard nil)
  (foreach p sorted-pieces
    (cond
      (stopGuard
       (setq skip (1+ skip)))
      ((> p stock)
       (setq skip (1+ skip)))
      (T
        (setq placed nil j 0)
        (while (and (not placed) (< j (length bars)) (not stopGuard))
          (setq bar (nth j bars))
          (setq attempts (1+ attempts))
          (if (>= attempts *n1-max-placement-attempts*)
            (setq stopGuard T)
            (if (>= (car bar) (+ kerf p))
              (progn
                (setq newbar (cons (- (car bar) kerf p)
                                   (append (cdr bar) (list p))))
                (setq bars (n1-replace-nth bars j newbar))
                (setq placed T)
              )
            )
          )
          (setq j (1+ j))
        )
        (if (not placed)
          (if stopGuard
            (setq skip (1+ skip))
            (setq bars (append bars (list (list (- stock p) p))))
          )
        )
      )
    )
  )
  (if stopGuard
    (princ (strcat "\n[CUTLINE][GUARD] Алгоритм остановлен ограничителем попыток ("
                    (itoa *n1-max-placement-attempts*) "). Размещено: "
                    (itoa (- (length sorted-pieces) skip)) "/"
                    (itoa (length sorted-pieces)))))
  (if (> skip 0)
    (princ (strcat "\nВНИМАНИЕ: в FFD пропущено деталей длиннее хлыста: " (itoa skip)))
  )
  bars
)

;; ============================================================
;; МАРКИ ДЕТАЛЕЙ
;; Решатель FFD работает с голыми длинами: связь детали с исходным
;; объектом теряется ещё при группировке по длине, а трогать решатель
;; нельзя. Поэтому марки собираются в побочную очередь «длина -> марки»
;; при измерении и выдаются при отрисовке по длине детали.
;;
;; Следствие, которое надо знать: детали ОДНОЙ длины взаимозаменяемы —
;; это один и тот же рез, — поэтому марка может достаться соседней
;; детали той же длины. На раскрой и на длины это не влияет.
;; ============================================================

(setq *n1-marks* '())     ;; собранные при измерении: (ключ . список марок)
(setq *n1-marks-q* '())   ;; расходуемая копия на время отрисовки

;; Ключ длины: целые доли миллиметра, чтобы не сравнивать float напрямую
(defun n1-mark-key (len)
  (fix (+ (* (float len) 1000.0) 0.5)))

(defun n1-mark-add (len mk / k f)
  (if (and mk (= (type mk) 'STR) (/= mk ""))
    (progn
      (setq k (n1-mark-key len) f (assoc k *n1-marks*))
      (if f
        (setq *n1-marks* (subst (cons k (append (cdr f) (list mk))) f *n1-marks*))
        (setq *n1-marks* (cons (cons k (list mk)) *n1-marks*)))))
  mk)

;; Марки деталей данной длины — для перечня изделий. Берутся из
;; мастер-списка, который при отрисовке не расходуется.
(defun n1-marks-for (len / f)
  (setq f (assoc (n1-mark-key len) *n1-marks*))
  (if f (cdr f) '())
)

;; Строки перечня изделий: одна на каждую марку.
;; Было «первая марка +N» — читалось как часть названия («ТБ-1 Рг3ср +2»),
;; хотя означало «есть ещё 2 другие марки». Теперь длина с несколькими
;; марками даёт несколько строк с точным количеством по каждой, а изделия
;; без марки идут отдельной строкой с прочерком.
;; Решатель уже отработал — это только таблица, раскрой не меняется.
(defun n1-piece-rows (pieces / out rec len cnt marks seen m f nomark)
  (setq out '())
  (foreach rec pieces
    (setq len (car rec) cnt (cadr rec) marks (n1-marks-for len) seen '())
    ;; количество по каждой марке, порядок — как при измерении
    (foreach m marks
      (setq f (assoc m seen))
      (if f
        (setq seen (subst (cons m (1+ (cdr f))) f seen))
        (setq seen (append seen (list (cons m 1))))))
    (setq nomark (- cnt (length marks)))
    (if (null seen)
      (setq out (append out (list (list len cnt ""))))
      (progn
        (foreach f seen
          (setq out (append out (list (list len (cdr f) (car f))))))
        (if (> nomark 0)
          (setq out (append out (list (list len nomark "-")))))))
  )
  out
)

;; Копия очереди на отрисовку: повторный вызов отрисовки не остаётся без марок
(defun n1-marks-begin ()
  (setq *n1-marks-q* *n1-marks*))

;; Очередная марка для детали данной длины; nil, если марок больше нет
(defun n1-mark-take (len / k f v)
  (setq k (n1-mark-key len) f (assoc k *n1-marks-q*) v nil)
  (if (and f (cdr f))
    (progn
      (setq v (car (cdr f)))
      (setq *n1-marks-q* (subst (cons k (cdr (cdr f))) f *n1-marks-q*))))
  v)

(defun n1-add-group (groups key / found)
  (setq found (assoc key groups))
  (if found
    (mapcar '(lambda (x) (if (= (car x) key) (cons (car x) (1+ (cdr x))) x)) groups)
    (cons (cons key 1) groups)
  )
)

;; ============================================================
;; Подсчет объектов по типам
;; ============================================================
(defun n1-count-by-type (ss / i ent typ counts found obj len)
  (setq counts '(("LINE" . 0) ("MLINE" . 0) ("DYNBLOCK" . 0)) i 0)
  (repeat (sslength ss)
    (setq ent (ssname ss i))
    (setq typ (cdr (assoc 0 (entget ent))))
    (cond
      ((or (= typ "LINE") (= typ "MLINE"))
       (setq found (assoc typ counts))
       (if found (setq counts (subst (cons typ (1+ (cdr found))) found counts)))
      )
      ((= typ "INSERT")
       (setq obj (vl-catch-all-apply 'vlax-ename->vla-object (list ent)))
       (if (and
             (not (vl-catch-all-error-p obj))
             (su-is-valid-stock-block obj))
         (progn
           (setq found (assoc "DYNBLOCK" counts))
           (if found (setq counts (subst (cons "DYNBLOCK" (1+ (cdr found))) found counts)))
         )
       )
      )
    )
    (setq i (1+ i))
  )
  counts
)

(defun n1-print-type-counts (counts / s rec)
  (setq s "")
  (foreach rec counts
    (if (> (cdr rec) 0)
      (setq s (strcat s (if (= s "") "" ", ")
                      (itoa (cdr rec)) " "
                      (cond ((= (car rec) "LINE")      "линий")
                            ((= (car rec) "MLINE")     "мультилиний")
                            ((= (car rec) "DYNBLOCK")  "дин. блоков")
                            (T (strcat (car rec) " шт")))))
    )
  )
  (if (= s "")
    (princ "\n  (объектов подходящих типов нет)")
    (princ (strcat "\n  " s))
  )
)

;; ============================================================
;; Фильтрация набора по типу
;; ============================================================
(defun n1-filter-ss-by-type (ss typ / i ent new-ss ent-typ obj)
  (setq new-ss (ssadd) i 0)
  (repeat (sslength ss)
    (setq ent (ssname ss i))
    (setq ent-typ (cdr (assoc 0 (entget ent))))
    (cond
      ((or (= typ "LINE") (= typ "MLINE"))
       (if (= ent-typ typ) (ssadd ent new-ss))
      )
      ((= typ "DYNBLOCK")
       (if (= ent-typ "INSERT")
         (progn
           (setq obj (vl-catch-all-apply 'vlax-ename->vla-object (list ent)))
           (if (and
                 (not (vl-catch-all-error-p obj))
                 (su-is-valid-stock-block obj))
             (ssadd ent new-ss)
           )
         )
       )
      )
      ((= typ "ALL")
       (ssadd ent new-ss)
      )
    )
    (setq i (1+ i))
  )
  new-ss
)

;; ============================================================
;; Фильтрация набора по типу И имени типа блока
;; ============================================================
(defun n1-filter-ss-by-type-and-name (ss typ type-name
                                      / i ent new-ss ent-typ obj block-type-name)
  (setq new-ss (ssadd) i 0)
  (repeat (sslength ss)
    (setq ent (ssname ss i))
    (setq ent-typ (cdr (assoc 0 (entget ent))))
    (cond
      ((or (= typ "LINE") (= typ "MLINE"))
       (if (= ent-typ typ) (ssadd ent new-ss))
      )
      ((= typ "DYNBLOCK")
       (if (= ent-typ "INSERT")
         (progn
           (setq obj (vl-catch-all-apply 'vlax-ename->vla-object (list ent)))
           (if (and (not (vl-catch-all-error-p obj))
                    (su-is-valid-stock-block obj))
             (progn
               (if (or (null type-name)
                       (= type-name "")
                       (= type-name "Все типы блоков"))
                 (ssadd ent new-ss)
                 (progn
                   (setq block-type-name (su-get-dynblock-type-name ent))
                   (if (= block-type-name type-name)
                     (ssadd ent new-ss)
                   )
                 )
               )
             )
           )
         )
       )
      )
      ((= typ "ALL")
       (ssadd ent new-ss)
      )
    )
    (setq i (1+ i))
  )
  new-ss
)

;; ============================================================
;; Фильтрация набора по типу мультилинии
;; ============================================================
(defun n1-filter-ss-by-mline-type (ss type-name / i ent new-ss)
  (setq new-ss (ssadd) i 0)
  (repeat (sslength ss)
    (setq ent (ssname ss i))
    (if (= (cdr (assoc 0 (entget ent))) "MLINE")
      (if (or (null type-name) (= type-name "")
              (= (su-mline-type-name ent) type-name))
        (ssadd ent new-ss)
      )
    )
    (setq i (1+ i))
  )
  new-ss
)

;; ============================================================
;; Подсчет динамических блоков конкретного типа
;; ============================================================
(defun n1-count-dynblock-by-type (ss type-name
                                  / i ent typ obj count block-type-name)
  (setq count 0 i 0)
  (if (null ss)
    0
    (progn
      (repeat (sslength ss)
        (setq ent (ssname ss i))
        (setq typ (cdr (assoc 0 (entget ent))))
        (if (= typ "INSERT")
          (progn
            (setq obj (vl-catch-all-apply 'vlax-ename->vla-object (list ent)))
            (if (and (not (vl-catch-all-error-p obj))
                     (su-is-valid-stock-block obj))
              (progn
                (if (or (null type-name)
                        (= type-name "")
                        (= type-name "Все типы блоков"))
                  (setq count (1+ count))
                  (progn
                    (setq block-type-name (su-get-dynblock-type-name ent))
                    (if (= block-type-name type-name)
                      (setq count (1+ count))
                    )
                  )
                )
              )
            )
          )
        )
        (setq i (1+ i))
      )
      count
    )
  )
)

(defun n1-filter-name-str ( / s)
  ;; Ред. 14: общая система фильтров диспетчера (extraction.lsp, ред. 2).
  ;; Возвращает «по фильтру: Мои» / «по фильтрам: Фасады, Окна» либо nil.
  (setq s nil)
  (if (= (type extraction-layer-filter-source-title) 'SUBR)
    (setq s (extraction-layer-filter-source-title))
  )
  s
)

;; ============================================================
;; Отображение списка слоев
;; ============================================================
(defun n1-layer-display-list (layers / fname suffix)
  (setq fname (n1-filter-name-str))
  (setq suffix "")

  (cond
    ((and (boundp '*CUTLINE-IS-AUTO-FILTER*)
          *CUTLINE-IS-AUTO-FILTER*
          fname)
     (setq suffix " (за исключением слоя 0)")
     (list (strcat fname suffix))
    )
    ((or (null layers) (not (listp layers)) (= (length layers) 0))
     (list "Все слои")
    )
    (T layers)
  )
)

;; «Фильтр Витражи» / «Фильтры Фасады, Окна» либо nil
(defun n1-filter-header-str ( / keys s)
  (setq s nil)
  (if (and (n1-filter-name-str)
           (= (type extraction-layer-filter-list-str) 'SUBR)
           (boundp '*EXTRACTION-LAYER-FILTERS*))
    (progn
      (setq keys *EXTRACTION-LAYER-FILTERS*)
      (setq s (extraction-layer-filter-list-str keys))
      (setq s
        (if (= s "")
          nil
          (strcat (if (= (length keys) 1) "Фильтр " "Фильтры ") s)))
    )
  )
  s
)

;; Заголовок рамки: «Выбранные слои (Фильтр Витражи: 31 слой)»
;; либо «Выбранные слои (3 слоя)» / «Выбранные слои (все слои)»
(defun n1-layers-header-text (layers / n f)
  (setq n (if (listp layers) (length layers) 0))
  (setq f (n1-filter-header-str))
  (cond
    (f (strcat "Выбранные слои (" f ": " (itoa n) " " (tu-layer-word n) ")"))
    ((<= n 0) "Выбранные слои (все слои)")
    (T (strcat "Выбранные слои (" (itoa n) " " (tu-layer-word n) ")"))
  )
)

;; Безопасные обертки
(defun n1-safe-set-tile (key value)
  (vl-catch-all-apply 'set_tile (list key value))
)
(defun n1-safe-action-tile (key action)
  (vl-catch-all-apply 'action_tile (list key action))
)
(defun n1-safe-mode-tile (key mode)
  (vl-catch-all-apply 'mode_tile (list key mode))
)

;; ============================================================
;; Ручное управление радиокнопками
;; ============================================================
(defun n1-select-radio (selected / keys k)
  (setq keys '("rb_line" "rb_mline" "rb_dynblock" "rb_both"))
  (foreach k keys
    (n1-safe-set-tile k (if (= k selected) "1" "0"))
  )
  (cond
    ((= selected "rb_line")     (setq *n1-tmp-choice* 'LINE))
    ((= selected "rb_mline")    (setq *n1-tmp-choice* 'MLINE))
    ((= selected "rb_dynblock") (setq *n1-tmp-choice* 'DYNBLOCK))
    ((= selected "rb_both")     (setq *n1-tmp-choice* 'ALL))
  )

  (if (= selected "rb_dynblock")
    (n1-safe-mode-tile "popup_dynblock_type" 0)
    (progn
      (n1-safe-mode-tile "popup_dynblock_type" 1)
      (setq *n1-tmp-dynblock-type* "")
    )
  )

  (if (= selected "rb_mline")
    (n1-safe-mode-tile "popup_mline_type" 0)
    (progn
      (n1-safe-mode-tile "popup_mline_type" 1)
      (setq *n1-tmp-mline-type* "")
    )
  )
)

;; ============================================================
;; Обработчик выбора типа динамического блока
;; ============================================================
(defun n1-on-dynblock-type-changed (value / idx type-name new-count)
  (setq idx (atoi value))
  (if (= idx 0)
    (progn
      (setq *n1-tmp-dynblock-type* "")
      (setq new-count (n1-count-dynblock-by-type *n1-cutline-ss* ""))
      (n1-safe-set-tile "txt_dynblock_count"
        (strcat (itoa new-count) " шт."))
    )
    (progn
      (setq type-name (nth (1- idx) *n1-dynblock-types-list*))
      (setq *n1-tmp-dynblock-type* type-name)
      (setq new-count (n1-count-dynblock-by-type *n1-cutline-ss* type-name))
      (n1-safe-set-tile "txt_dynblock_count"
        (strcat (itoa new-count) " шт."))
      (n1-select-radio "rb_dynblock")
    )
  )
)

;; ============================================================
;; Обработчик выбора типа мультилинии
;; ============================================================
(defun n1-on-mline-type-changed (value / idx type-name new-count)
  (setq idx (atoi value))
  (if (= idx 0)
    (progn
      (setq *n1-tmp-mline-type* "")
      (setq new-count (su-count-mline-by-type *n1-cutline-ss* ""))
      (n1-safe-set-tile "txt_mline_count"
        (strcat (itoa new-count) " шт."))
    )
    (progn
      (setq type-name (nth (1- idx) *n1-mline-types-list*))
      (setq *n1-tmp-mline-type* type-name)
      (setq new-count (su-count-mline-by-type *n1-cutline-ss* type-name))
      (n1-safe-set-tile "txt_mline_count"
        (strcat (itoa new-count) " шт."))
      (n1-select-radio "rb_mline")
    )
  )
)

;; ============================================================
;; Диалог параметров раскроя
;; ============================================================
;; Этап 2 (V1+V2): прием диалога = проверка введенных чисел.
;; Заменяет старый молчаливый пресет на дефолт: теперь мусор
;; в полях "хлыст"/"рез" не пропускается - диалог остается открытым.
(defun n1-dialog-accept (/ s k)
  (setq s *n1-tmp-stock* k *n1-tmp-kerf*)
  (if (and (tu-valid-bar-length-p s)
           (tu-valid-kerf-p k)
           (< k s))
    (done_dialog 1)
    (alert (strcat "[AutoExtraction][CUTLINE][VALIDATION]\n"
                   "Длина хлыста: число > 0 (лимит "
                   (rtos *n1-max-bar-length* 2 0) " мм).\n"
                   "Рез: число от 0 до " (rtos *n1-max-kerf* 2 0)
                   " мм и меньше длины хлыста."))
  )
)

(defun n1-cutline-dialog (line-cnt mline-cnt dynblock-cnt
                          ss-for-types
                          default-tol default-stock default-kerf
                          layers
                          default-xls default-acad
                          / dcl-file dcl-id result
                            all-cnt base-layers tn dcl-src)

  (setq dcl-src (findfile "cutline_filter.dcl"))

  ;; Заголовок рамки «Выбранные слои» статичен в DCL — подменяется
  ;; во временной копии файла; при неудаче берётся исходный файл
  (setq dcl-file
    (if dcl-src
      (tu-dcl-with-label dcl-src "label = \"Выбранные слои"
        (n1-layers-header-text (n1-layer-display-list layers)))
      nil))

  (if (null dcl-file)
    (progn
      (princ "\n[cutline] не найден cutline_filter.dcl")
      nil
    )
    (progn
      (setq dcl-id (load_dialog dcl-file))
      (if (< dcl-id 0)
        (progn
          (princ "\n[cutline] ошибка load_dialog")
          (tu-dcl-cleanup dcl-file dcl-src)
          nil
        )
        (progn
          (setq *n1-tmp-choice* 'ALL)
          (setq *n1-tmp-stock* default-stock)
          (setq *n1-tmp-kerf* default-kerf)
          (setq *n1-tmp-chk-xls* default-xls)
          (setq *n1-tmp-chk-acad* default-acad)

          (if (vl-catch-all-error-p
                (vl-catch-all-apply 'new_dialog (list "cutline_filter_dialog" dcl-id)))
            (progn
              (princ "\n[cutline] ошибка new_dialog")
              (vl-catch-all-apply 'unload_dialog (list dcl-id))
              (tu-dcl-cleanup dcl-file dcl-src)
              nil
            )
            (progn
              (setq all-cnt (+ line-cnt mline-cnt dynblock-cnt))

              (n1-safe-set-tile "txt_line_count"
                (strcat (itoa line-cnt) " шт."))
              (n1-safe-set-tile "txt_mline_count"
                (strcat (itoa mline-cnt) " шт."))
              (n1-safe-set-tile "txt_dynblock_count"
                (strcat (itoa dynblock-cnt) " шт."))
              (n1-safe-set-tile "txt_both_count"
                (strcat (itoa all-cnt) " шт."))

              (setq *n1-cutline-ss* ss-for-types)

              (setq *n1-tmp-dynblock-type* "")
              (setq *n1-dynblock-types-list*
                (su-collect-dynblock-types ss-for-types 'su-is-valid-stock-block))

              (start_list "popup_dynblock_type")
              (add_list "Все типы блоков")
              (foreach tn *n1-dynblock-types-list*
                (add_list tn)
              )
              (end_list)
              (set_tile "popup_dynblock_type" "0")

              (if (or (<= dynblock-cnt 0)
                      (and (not (eq *n1-tmp-choice* 'DYNBLOCK))
                           (not (eq *n1-tmp-choice* 'ALL))))
                (n1-safe-mode-tile "popup_dynblock_type" 1)
              )

              (setq *n1-tmp-mline-type* "")
              (setq *n1-mline-types-list*
                (su-collect-mline-types ss-for-types))

              (start_list "popup_mline_type")
              (add_list "Все типы мультилиний")
              (foreach tn *n1-mline-types-list*
                (add_list tn)
              )
              (end_list)
              (set_tile "popup_mline_type" "0")

              (if (or (<= mline-cnt 0)
                      (and (not (eq *n1-tmp-choice* 'MLINE))
                           (not (eq *n1-tmp-choice* 'ALL))))
                (n1-safe-mode-tile "popup_mline_type" 1)
              )

              (setq base-layers (n1-layer-display-list layers))
              (vl-catch-all-apply
                '(lambda ()
                   (start_list "lst_layers")
                   (foreach l base-layers (add_list l))
                   (end_list))
                nil)

              (cond
                ((and (> line-cnt 0) (> mline-cnt 0))
                 (n1-safe-set-tile "rb_both" "1")
                 (setq *n1-tmp-choice* 'ALL))
                ((and (> line-cnt 0) (> dynblock-cnt 0))
                 (n1-safe-set-tile "rb_both" "1")
                 (setq *n1-tmp-choice* 'ALL))
                ((and (> mline-cnt 0) (> dynblock-cnt 0))
                 (n1-safe-set-tile "rb_both" "1")
                 (setq *n1-tmp-choice* 'ALL))
                ((> line-cnt 0)
                 (n1-safe-set-tile "rb_line" "1")
                 (setq *n1-tmp-choice* 'LINE))
                ((> mline-cnt 0)
                 (n1-safe-set-tile "rb_mline" "1")
                 (setq *n1-tmp-choice* 'MLINE))
                ((> dynblock-cnt 0)
                 (n1-safe-set-tile "rb_dynblock" "1")
                 (setq *n1-tmp-choice* 'DYNBLOCK))
                (T
                 (n1-safe-set-tile "rb_both" "1")
                 (setq *n1-tmp-choice* 'ALL))
              )

              (if (<= line-cnt 0)     (n1-safe-mode-tile "rb_line" 1))
              (if (<= mline-cnt 0)    (n1-safe-mode-tile "rb_mline" 1))
              (if (<= dynblock-cnt 0) (n1-safe-mode-tile "rb_dynblock" 1))
              (if (<= all-cnt 0)      (n1-safe-mode-tile "rb_both" 1))

              (n1-safe-set-tile "edt_stock" (rtos default-stock 2 0))
              (n1-safe-set-tile "edt_kerf"  (rtos default-kerf 2 0))

              (n1-safe-set-tile "chk_xls"  (if default-xls  "1" "0"))
              (n1-safe-set-tile "chk_acad" (if default-acad "1" "0"))

              (n1-safe-action-tile "rb_line"     "(n1-select-radio \"rb_line\")")
              (n1-safe-action-tile "rb_mline"    "(n1-select-radio \"rb_mline\")")
              (n1-safe-action-tile "rb_dynblock" "(n1-select-radio \"rb_dynblock\")")
              (n1-safe-action-tile "rb_both"     "(n1-select-radio \"rb_both\")")

              (n1-safe-action-tile "popup_dynblock_type"
                "(n1-on-dynblock-type-changed $value)")
              (n1-safe-action-tile "popup_mline_type"
                "(n1-on-mline-type-changed $value)")

              (n1-safe-action-tile "edt_stock"
                "(setq *n1-tmp-stock* (tu-parse-number $value))")
              (n1-safe-action-tile "edt_kerf"
                "(setq *n1-tmp-kerf* (tu-parse-number $value))")

              (n1-safe-action-tile "chk_xls"
                "(setq *n1-tmp-chk-xls* (= $value \"1\"))")
              (n1-safe-action-tile "chk_acad"
                "(setq *n1-tmp-chk-acad* (= $value \"1\"))")

              (n1-safe-action-tile "btn_ok"     "(n1-dialog-accept)")
              (n1-safe-action-tile "btn_cancel" "(done_dialog 0)")

              (setq result (start_dialog))

              (vl-catch-all-apply 'unload_dialog (list dcl-id))
              (tu-dcl-cleanup dcl-file dcl-src)

              (if (= result 1)
                (list
                  *n1-tmp-choice*
                  default-tol
                  *n1-tmp-stock*
                  *n1-tmp-kerf*
                  *n1-tmp-chk-xls*
                  *n1-tmp-chk-acad*
                  *n1-tmp-dynblock-type*
                  *n1-tmp-mline-type*
                )
                nil
              )
            )
          )
        )
      )
    )
  )
)

;; ============================================================
;; Извлечение длин
;; ============================================================
;; V4: контракт отбраковки - модель CUTSHEET (cs-reject-note/cs-print-rejects):
;; *n1-rejects*       - assoc-счетчик причин отсева за сбор: (причина . количество);
;; *n1-reject-reason* - причина, выставленная последней попыткой измерения.
;; Каждый отброшенный объект учитывается в регистре РОВНО ОДИН раз с причиной
;; (в старой схеме сломанные/диагональные MLINE учитывались дважды - в своей
;; категории и в общей "нулевые/ошибки").
(defun n1-reject-note (reason / cell)
  (if (or (null reason) (= reason "")) (setq reason "причина не зафиксирована"))
  (setq cell (assoc reason *n1-rejects*))
  (if cell
    (setq *n1-rejects* (subst (cons reason (1+ (cdr cell))) cell *n1-rejects*))
    (setq *n1-rejects* (cons (cons reason 1) *n1-rejects*))))

(defun n1-print-rejects ( / cell total)
  (setq total 0)
  (foreach cell *n1-rejects* (setq total (+ total (cdr cell))))
  (if (> total 0)
    (progn
      (princ (strcat "\n[CUTLINE][VALIDATION] Исключено объектов: " (itoa total)))
      (foreach cell (reverse *n1-rejects*)
        (princ (strcat "\n  " (car cell) ": " (itoa (cdr cell))))))))

(defun n1-extract-pieces (ss tol min-len max-len /
                            i ent typ len key pieces total geom
                            measured obj)
  (setq pieces '() i 0 total (sslength ss) measured 0
        *n1-rejects* '() *n1-reject-reason* nil *n1-marks* '())
  (repeat total
    (setq ent (ssname ss i))
    (setq typ (cdr (assoc 0 (entget ent))))
    (setq *n1-reject-reason* nil)

    (cond
      ((= typ "MLINE")
       (setq geom (su-mline-cut-geom ent))
       (if geom
         (setq len (car geom))
         (progn
           (setq len nil)
           (if (> (su-mline-vertex-count ent) 2)
             (setq *n1-reject-reason* "MLINE: ломаная (больше 2 вершин)")
             (setq *n1-reject-reason* "MLINE: диагональная")
           )
         )
       )
      )
      ((= typ "LINE")
       (setq len (vl-catch-all-apply 'vlax-curve-getDistAtParam
                   (list ent (vlax-curve-getEndParam ent))))
       (if (vl-catch-all-error-p len)
         (setq len nil *n1-reject-reason* "LINE: длина недоступна (ActiveX)"))
      )
      ((= typ "INSERT")
       (setq obj (vl-catch-all-apply 'vlax-ename->vla-object (list ent)))
       (if (vl-catch-all-error-p obj)
         (setq len nil *n1-reject-reason* "ActiveX объекта недоступен")
         (progn
           (setq len (su-get-length obj (ae-settings-task-length-props 'CUTLINE)))
           (if (null len)
             (setq *n1-reject-reason*
               "длина не определена (нет свойства по маскам input.block.length)")))
       )
      )
      (T
       (setq len nil)
       (setq *n1-reject-reason* "неподдерживаемый тип объекта"))
    )

    (cond
      ((or (null len) (not (numberp len)))
       (n1-reject-note
         (if *n1-reject-reason* *n1-reject-reason* "длина не определена")))
      ((<= len 0.0)
       (n1-reject-note "длина <= 0"))
      ((< len min-len)
       (n1-reject-note (strcat "короче минимума (" (rtos min-len 2 0) " мм)")))
      ((> len max-len)
       (n1-reject-note (strcat "длиннее максимума (" (rtos max-len 2 0) " мм)")))
      (T (setq measured (1+ measured))
         (setq key (fix (+ (/ len tol) 0.5)))
         ;; марка берётся по ОКРУГЛЁННОЙ длине — ровно та, что уйдёт в решатель
         (n1-mark-add (* (float key) tol) (tu-entity-mark ent))
         (setq pieces (n1-add-group pieces key)))
    )
    (setq i (1+ i))
  )
  (princ (strcat "\nИзмерено: " (itoa measured) " из " (itoa total)))
  (n1-print-rejects)
  (mapcar '(lambda (x) (list (* (float (car x)) tol) (cdr x)))
          (reverse pieces))
)

(defun n1-split-by-stock (pieces stock / ok oversized rec)
  (setq ok '() oversized '())
  (foreach rec pieces
    (if (<= (car rec) stock)
      (setq ok (cons rec ok))
      (setq oversized (cons rec oversized))
    )
  )
  (list (reverse ok) (reverse oversized))
)

;; ============================================================
;; Вывод неразмещенных деталей
;; ============================================================
(defun n1-report-oversized (oversized stock / rec total-cnt sorted)
  (if oversized
    (progn
      (princ "\n")
      (princ "\n=== НЕРАЗМЕЩЕННЫЕ ДЕТАЛИ ===")
      (princ (strcat "\n(длина превышает хлыст " (rtos stock 2 0) " мм)"))

      (setq sorted (vl-sort oversized '(lambda (a b) (> (car a) (car b)))))

      (setq total-cnt 0)
      (foreach rec sorted
        (setq total-cnt (+ total-cnt (cadr rec)))
        (princ (strcat "\n  Длина " (rtos (car rec) 2 0)
                       " мм, кол-во " (itoa (cadr rec)) " шт."))
      )
      (princ (strcat "\nВсего неразмещенных: " (itoa total-cnt) " шт."))
    )
  )
)

;; ============================================================
;; Преобразование списка длин в строку
;; ============================================================
(defun n1-list-to-str (lst sep / s x)
  ;; Разделитель по умолчанию " + ": Excel сливает "2000 2000" в число
  (if (null sep) (setq sep " + "))
  (setq s "")
  (foreach x lst
    (setq s (strcat s (if (= s "") "" sep) (itoa (fix x))))
  )
  s
)

;; ============================================================
;; Раскладка хлыстов
;; ============================================================
(defun n1-draw-layout (bars stock kerf insPt color-map /
    barHeight gap txtH axisStep x0 y0 maxy miny i bar pieces waste used util pgi pgn
    curx p str col labelX labelY1 labelY2 centerY
    waste-txt-h waste-center-y waste-x mk mkH drawMk markW sizeW textX)

  ;; ============================================================
  ;; ПАРАМЕТРЫ РАСКЛАДКИ (РЕГУЛИРОВАТЬ ЗДЕСЬ)
  ;; ============================================================
  ;; ОСЕВОЕ РАССТОЯНИЕ между хлыстами. Регулировать здесь.
  (setq axisStep (* (/ stock 30.0) 1.7))
  ;; ВЫСОТА ХЛЫСТА. Делитель: чем больше, тем тоньше хлыст.
  (setq barHeight (/ stock 45.0))
  ;; Зазор между хлыстами вычисляется автоматически
  (setq gap (- axisStep barHeight))
  ;; ВЫСОТА ТЕКСТА (фиксирована, НЕ зависит от высоты хлыста)
  (setq txtH (* (/ stock 30.0) 0.30))
  ;; ============================================================

  (setq x0 (car insPt) y0 (cadr insPt) maxy (+ y0 barHeight) miny y0 i 0)
  ;; свежая копия очереди марок: повторная отрисовка не остаётся без них
  (n1-marks-begin)
  ;; П3 (п.20): прогресс в статусной строке
  (setq pgi 0 pgn (length bars))
  (foreach bar bars
    (setq pgi (1+ pgi))
    (grtext -1 (strcat "CUTLINE: отрисовка хлыста " (itoa pgi) " из " (itoa pgn)))
    (setq i (1+ i))
    (setq pieces (cdr bar) waste (car bar) used (- stock waste)
          util (* 100.0 (/ used stock)) miny y0)
    (setq curx x0)

    ;; ЗАЛИВКА ДЕТАЛЕЙ
    (foreach p pieces
      (setq col (n1-get-color color-map p))
      (n1-draw-filled-rect (list curx y0) (list (+ curx p) (+ y0 barHeight))
                           col *CUTLINE-PART-TRANSPARENCY*)
      (setq curx (+ curx p kerf))
    )

    ;; ЗАЛИВКА ОТХОДА
    (if (> waste 0.0)
      (n1-draw-filled-rect (list (- (+ x0 stock) waste) y0)
                           (list (+ x0 stock) (+ y0 barHeight))
                           *NEST-COLOR-WASTE* *CUTLINE-WASTE-TRANSPARENCY*)
    )

    ;; Обводка хлыста
    (n1-draw-rect (list x0 y0) (list (+ x0 stock) (+ y0 barHeight)) *NEST-COLOR-OUTLINE*)

    ;; ВЕРТИКАЛЬНЫЕ ЛИНИИ РЕЗА (две на деталь: граница детали + граница реза)
    (setq curx x0)
    (foreach p pieces
      (n1-draw-line (list curx y0) (list curx (+ y0 barHeight)) *NEST-COLOR-OUTLINE*)
      (n1-draw-line (list (+ curx p) y0) (list (+ curx p) (+ y0 barHeight)) *NEST-COLOR-OUTLINE*)
      (setq curx (+ curx p kerf))
    )
    (n1-draw-line (list curx y0) (list curx (+ y0 barHeight)) *NEST-COLOR-OUTLINE*)

    ;; Метки хлыста: выравнивание по правому краю, вертикально от центра хлыста
    ;; 0.6 — отступ левее от хлыста
    ;; 1.0 — половина расстояния между метками
    (setq labelX (- x0 (* barHeight 0.6)))
    (setq centerY (+ y0 (* barHeight 0.5)))
    (setq labelY1 (+ centerY (* txtH 1.0)))
    (setq labelY2 (- centerY (* txtH 1.0)))
    (n1-draw-text-right (list labelX labelY1) txtH
                        (strcat "Хлыст " (itoa i))
                        *NEST-COLOR-LABEL*)
    (n1-draw-text-right (list labelX labelY2) txtH
                        (strcat "[" (rtos util 2 1) "%]")
                        *NEST-COLOR-LABEL*)

    ;; ТЕКСТ ВНУТРИ ДЕТАЛЕЙ (жирный, желтый, середина)
    (setq curx x0)
    (foreach p pieces
      (setq str (itoa (fix p)))
      ;; Марка считается ПЕРВОЙ: деталь на хлысте — узкая полоса, обе
      ;; подписи идут в один ряд, поэтому габарит центрируется не по
      ;; всей детали, а по месту, оставшемуся справа от марки.
      (setq mk (n1-mark-take p))
      (setq mkH (if mk (* txtH 0.75) 0.0))
      (setq markW (if mk (+ (* mkH 0.35) (* (strlen mk) mkH 0.6)) 0.0))
      (setq sizeW (* (strlen str) txtH 1.1 0.6))
      ;; обе подписи влезают, только если хватает места по длине детали
      ;; марка растёт вверх от середины: нужна половина высоты плюс запас
      (setq drawMk (and mk
                        (> barHeight (* mkH 2.2))
                        (> p (+ markW sizeW (* mkH 0.5)))))
      (if (not drawMk) (setq markW 0.0))
      (setq textX (+ curx markW (* (- p markW) 0.5)))
      (n1-draw-text-bold-center (list textX (+ y0 (* barHeight 0.5)))
                                (* txtH 1.1) str *NEST-COLOR-PART-TEXT* 0.0)
      (if drawMk
        ;; марка на той же базовой линии, что и длина: подписи читаются
        ;; одной строкой. Высоты разные (0.75 против 1.1), поэтому
        ;; совпадают низы букв — так и выравнивают текст в строке.
        (n1-draw-text (list (+ curx (* mkH 0.35)) (+ y0 (* barHeight 0.5)))
                      mkH mk *CUTLINE-MARK-COLOR*))
      (setq curx (+ curx p kerf))
    )

    ;; ТЕКСТ ОТХОДА (длина, поворот 90°, по центру хлыста, отступ 0.75)
    (if (> waste 0.0)
      (progn
        (setq str (itoa (fix waste)))
        (setq waste-txt-h (* txtH 1.25))
        (setq waste-center-y (+ y0 (* barHeight 0.5)))
        (setq waste-x (+ x0 stock (* barHeight 0.75)))
        (n1-draw-text-bold-center (list waste-x waste-center-y)
                                  waste-txt-h str *NEST-COLOR-WASTE* 90.0)
      )
    )
    ;; Переход к следующему хлысту (осевое расстояние = barHeight + gap = axisStep)
    (setq y0 (- y0 barHeight gap))
  )
  (list (list (- x0 (* barHeight 2.0)) miny) (list (+ x0 stock) maxy))
)

;; ============================================================
;; Сводная таблица раскроя
;; ============================================================
(defun n1-draw-summary (bars pieces stock insPt color-map oversized /
    barHeight th rowH pad col1W colMW col2W col3W tableW tableH
    left top x1 xM x2 x3 y bottom hasMarks
    num-bars stock-total-mm stock-total-m
    total-cnt total-product-mm total-product-m kpd rec oversized-cnt
    num-piece-rows rows)
  (setq barHeight (/ stock 30.0) th (* barHeight 0.30)
        rowH (* barHeight 0.6) pad (* barHeight 0.6))
  ;; Колонка «Марка» появляется, только если марки есть. Ширина таблицы
  ;; при этом НЕ меняется: сумма колонок та же (13.0 долей barHeight),
  ;; просто перераспределена.
  (setq hasMarks nil)
  (foreach rec pieces
    (if (n1-marks-for (car rec)) (setq hasMarks T)))
  ;; порядок важен: ширины колонок зависят от hasMarks, а строки от марок
  ;; Ширины подобраны по заголовкам: «Изделие, мм» и «Сумма, м.п.» по
  ;; 11 знаков, «Кол-во, шт» 10. Прежнее 2.6 для «Кол-во» было тесным —
  ;; заголовок не помещался. Марка стоит ближе к «Изделие».
  (if hasMarks
    (setq col1W (* barHeight 3.1) colMW (* barHeight 3.95)
          col2W (* barHeight 2.85) col3W (* barHeight 3.1))
    (setq col1W (* barHeight 5.0) colMW 0.0
          col2W (* barHeight 3.5) col3W (* barHeight 4.5)))
  (setq tableW (+ col1W colMW col2W col3W (* pad 2)))
  (setq num-bars (length bars) stock-total-mm (* num-bars stock)
        stock-total-m (/ stock-total-mm 1000.0))
  (setq total-cnt 0 total-product-mm 0.0)
  (foreach rec pieces
    (setq total-cnt (+ total-cnt (cadr rec)))
    (setq total-product-mm (+ total-product-mm (* (car rec) (cadr rec))))
  )
  (setq total-product-m (/ total-product-mm 1000.0))
  (setq kpd (if (> stock-total-mm 0)
              (* 100.0 (/ (float total-product-mm) (float stock-total-mm))) 0.0))

  (setq pieces (vl-sort pieces '(lambda (a b) (> (car a) (car b)))))
  ;; перечень разбивается по маркам: строк становится больше, высота
  ;; таблицы пересчитывается ниже по их фактическому числу
  (setq rows (n1-piece-rows pieces))
  (setq num-piece-rows (length rows))

  (setq left (car insPt) top (cadr insPt))

  (setq tableH (+ (* pad 2)
                  (* (+ 9.0 num-piece-rows (if oversized 1.0 0.0)) rowH)))

  (setq bottom (- top tableH))
  (setq x1 (+ left pad)
        xM (+ left pad col1W)
        x2 (+ left pad col1W colMW)
        x3 (+ left pad col1W colMW col2W))

  (n1-draw-rect (list left bottom) (list (+ left tableW) top) *NEST-COLOR-OUTLINE*)

  (setq y (- top pad rowH))

  (n1-draw-text (list x1 y) (* th 1.3) "Раскрой хлыста" *NEST-COLOR-TITLE*)

  (setq y (- y rowH))
  (n1-draw-text (list x1 y) th "Хлыст, мм" *NEST-COLOR-HEADER*)
  (n1-draw-text (list x2 y) th "Кол-во, шт" *NEST-COLOR-HEADER*)
  (n1-draw-text (list x3 y) th "Сумма, м.п." *NEST-COLOR-HEADER*)

  (setq y (- y rowH))
  (n1-draw-text (list x1 y) th (itoa (fix stock)) *NEST-COLOR-VALUE*)
  (n1-draw-text (list x2 y) th (itoa num-bars) *NEST-COLOR-VALUE*)
  (n1-draw-text (list x3 y) th (rtos stock-total-m 2 2) *NEST-COLOR-VALUE*)

  (setq y (- y rowH))
  (n1-draw-text (list x1 y) th "Изделие, мм" *NEST-COLOR-HEADER*)
  (if hasMarks
    (n1-draw-text (list xM y) th "Марка" *NEST-COLOR-HEADER*))
  (n1-draw-text (list x2 y) th "Кол-во, шт" *NEST-COLOR-HEADER*)
  (n1-draw-text (list x3 y) th "Сумма, м.п." *NEST-COLOR-HEADER*)

  (setq y (- y rowH))
  (foreach rec rows
    (n1-draw-text (list x1 y) th (itoa (fix (car rec)))
                  (n1-get-color color-map (car rec)))
    (if hasMarks
      (n1-draw-text (list xM y) th
                    (tu-marks-brief (list (caddr rec))
                                    (tu-fit-chars colMW th))
                    *NEST-COLOR-VALUE*))
    (n1-draw-text (list x2 y) th (itoa (cadr rec)) *NEST-COLOR-VALUE*)
    (n1-draw-text (list x3 y) th
                  (rtos (/ (* (car rec) (cadr rec)) 1000.0) 2 2) *NEST-COLOR-VALUE*)
    (setq y (- y rowH))
  )

  (setq y (- y (* rowH 0.5)))
  (n1-draw-text (list x1 y) th (strcat "Всего изделий: " (itoa total-cnt) " шт")
                *NEST-COLOR-VALUE*)
  (setq y (- y rowH))
  (n1-draw-text (list x1 y) th
                (strcat "Суммарная длина: " (rtos total-product-m 2 2) " м.п.")
                *NEST-COLOR-VALUE*)
  (setq y (- y rowH))
  (n1-draw-text (list x1 y) (* th 1.2)
                (strcat "КПД использования: " (rtos kpd 2 1) " %")
                *NEST-COLOR-KPD*)

  (if oversized
    (progn
      (setq oversized-cnt 0)
      (foreach rec oversized
        (setq oversized-cnt (+ oversized-cnt (cadr rec)))
      )
      (setq y (- y rowH))
      (n1-draw-text (list x1 y) th
                    (strcat "Неразмещенных: " (itoa oversized-cnt)
                            " шт (см. таблицу ниже)")
                    *NEST-COLOR-KPD*)
    )
  )

  (list (list left bottom) (list (+ left tableW) top))
)

;; ============================================================
;; Таблица неразмещенных деталей
;; ============================================================
(defun n1-draw-oversized (oversized stock insPt /
    barHeight th rowH pad pad-bottom col1W col2W col3W tableW tableH
    left top x1 x2 x3 y bottom total-cnt rec)
  (if (null oversized)
    nil
    (progn
      (setq barHeight (/ stock 30.0) th (* barHeight 0.30)
            rowH (* barHeight 0.6) pad (* barHeight 0.6)
            pad-bottom (* barHeight 1.4)
            col1W (* barHeight 5.0) col2W (* barHeight 3.5) col3W (* barHeight 4.5))
      (setq tableW (+ col1W col2W col3W (* pad 2)))
      (setq total-cnt 0)
      (foreach rec oversized (setq total-cnt (+ total-cnt (cadr rec))))
      (setq left (car insPt) top (cadr insPt))

      (setq tableH (+ pad pad-bottom (* (+ 4.0 (length oversized)) rowH)))
      (setq bottom (- top tableH))
      (setq x1 (+ left pad) x2 (+ left pad col1W) x3 (+ left pad col1W col2W))

      (n1-draw-rect (list left bottom) (list (+ left tableW) top) *NEST-COLOR-OUTLINE*)

      (setq y (- top pad rowH))

      (n1-draw-text (list x1 y) (* th 1.3) "Неразмещенные детали" *NEST-COLOR-TITLE*)

      (setq y (- y rowH))
      (n1-draw-text (list x1 y) th
                    (strcat "(длина превышает хлыст " (rtos stock 2 0) " мм)")
                    *NEST-COLOR-VALUE*)

      (setq oversized (vl-sort oversized '(lambda (a b) (> (car a) (car b)))))

      (setq y (- y rowH))
      (n1-draw-text (list x1 y) th "Длина, мм" *NEST-COLOR-HEADER*)
      (n1-draw-text (list x2 y) th "Кол-во, шт" *NEST-COLOR-HEADER*)
      (n1-draw-text (list x3 y) th "Сумма, м.п." *NEST-COLOR-HEADER*)

      (setq y (- y rowH))
      (foreach rec oversized
        (n1-draw-text (list x1 y) th (itoa (fix (car rec))) *NEST-COLOR-VALUE*)
        (n1-draw-text (list x2 y) th (itoa (cadr rec)) *NEST-COLOR-VALUE*)
        (n1-draw-text (list x3 y) th
                      (rtos (/ (* (car rec) (cadr rec)) 1000.0) 2 2)
                      *NEST-COLOR-VALUE*)
        (setq y (- y rowH))
      )

      (setq y (- y (* rowH 0.5)))
      (n1-draw-text (list x1 y) th (strcat "Всего: " (itoa total-cnt) " шт")
                    *NEST-COLOR-KPD*)

      (list (list left bottom) (list (+ left tableW) top))
    )
  )
)

(defun n1-combine-bbox (b1 b2)
  (list (list (min (car (car b1)) (car (car b2)))
              (min (cadr (car b1)) (cadr (car b2))))
        (list (max (car (cadr b1)) (car (cadr b2)))
              (max (cadr (cadr b1)) (cadr (cadr b2))))))

;; ============================================================
;; Консольный отчет по хлыстам
;; ============================================================
(defun n1-report (bars stock kerf / i bar pieces waste used util)
  (princ (strcat "\nКоличество хлыстов: " (itoa (length bars))))
  (setq i 0)
  (foreach bar bars
    (setq i (1+ i))
    (setq pieces (cdr bar) waste (car bar) used (- stock waste)
          util (* 100.0 (/ used stock)))
    (princ (strcat "\nХлыст " (itoa i) ": " (n1-list-to-str pieces " + ")
                   " | исп. " (rtos used 2 1) " | Отход " (rtos waste 2 1)
                   " | " (rtos util 2 1) "%"))
  )
  (princ)
)

;; ============================================================
;; XLS-экспорт
;; ============================================================
(defun n1-write-xls (bars stock kerf oversized
                     num-bars stock-total-mm product-total-mm kpd all-pieces /
                     fname f i bar pieces waste used util rec
                     total-cnt-unplaced total-sum-unplaced
                     hasMarks rows rw)
  (setq fname (strcat (getvar "DWGPREFIX")
                      (vl-filename-base (getvar "DWGNAME"))
                      " Раскрой хлыстов.xls"))
  (setq f (open fname "w"))
  (if (null f)
    nil
    (progn
      (setq total-cnt-unplaced 0 total-sum-unplaced 0.0)

      (if oversized
        (progn
          (setq oversized (vl-sort oversized '(lambda (a b) (> (car a) (car b)))))
          (foreach rec oversized
            (setq total-cnt-unplaced (+ total-cnt-unplaced (cadr rec)))
            (setq total-sum-unplaced (+ total-sum-unplaced
                                        (/ (* (car rec) (cadr rec)) 1000.0)))
          )
        )
      )

      (eu-doc-begin f "FULL")
(write-line " <Styles>" f)

      (write-line "  <Style ss:ID=\"Default\" ss:Name=\"Normal\">" f)
      (write-line "   <Alignment ss:Vertical=\"Center\"/>" f)
      (write-line "  </Style>" f)

      (write-line "  <Style ss:ID=\"Data\">" f)
      (write-line "   <Alignment ss:Vertical=\"Center\"/>" f)
      (write-line "   <Borders>" f)
      (write-line "    <Border ss:Position=\"Bottom\" ss:LineStyle=\"Continuous\" ss:Weight=\"1\"/>" f)
      (write-line "    <Border ss:Position=\"Left\" ss:LineStyle=\"Continuous\" ss:Weight=\"1\"/>" f)
      (write-line "    <Border ss:Position=\"Right\" ss:LineStyle=\"Continuous\" ss:Weight=\"1\"/>" f)
      (write-line "    <Border ss:Position=\"Top\" ss:LineStyle=\"Continuous\" ss:Weight=\"1\"/>" f)
      (write-line "   </Borders>" f)
      (write-line "  </Style>" f)

      (write-line "  <Style ss:ID=\"Header\">" f)
      (write-line "   <Font ss:Bold=\"1\" ss:Size=\"12\" ss:Underline=\"Single\"/>" f)
      (write-line "   <Interior ss:Color=\"#D9D9D9\" ss:Pattern=\"Solid\"/>" f)
      (write-line "   <Alignment ss:Horizontal=\"Center\" ss:Vertical=\"Center\"/>" f)
      (write-line "   <Borders>" f)
      (write-line "    <Border ss:Position=\"Bottom\" ss:LineStyle=\"Continuous\" ss:Weight=\"1\"/>" f)
      (write-line "    <Border ss:Position=\"Left\" ss:LineStyle=\"Continuous\" ss:Weight=\"1\"/>" f)
      (write-line "    <Border ss:Position=\"Right\" ss:LineStyle=\"Continuous\" ss:Weight=\"1\"/>" f)
      (write-line "    <Border ss:Position=\"Top\" ss:LineStyle=\"Continuous\" ss:Weight=\"1\"/>" f)
      (write-line "   </Borders>" f)
      (write-line "  </Style>" f)

      (write-line "  <Style ss:ID=\"ReportTitle\">" f)
      (write-line "   <Font ss:Bold=\"1\" ss:Size=\"12\" ss:Underline=\"Single\"/>" f)
      (write-line "   <Interior ss:Color=\"#D9D9D9\" ss:Pattern=\"Solid\"/>" f)
      (write-line "   <Alignment ss:Horizontal=\"Center\" ss:Vertical=\"Center\"/>" f)
      (write-line "   <Borders>" f)
      (write-line "    <Border ss:Position=\"Bottom\" ss:LineStyle=\"Continuous\" ss:Weight=\"2\"/>" f)
      (write-line "    <Border ss:Position=\"Left\" ss:LineStyle=\"Continuous\" ss:Weight=\"2\"/>" f)
      (write-line "    <Border ss:Position=\"Right\" ss:LineStyle=\"Continuous\" ss:Weight=\"2\"/>" f)
      (write-line "    <Border ss:Position=\"Top\" ss:LineStyle=\"Continuous\" ss:Weight=\"2\"/>" f)
      (write-line "   </Borders>" f)
      (write-line "  </Style>" f)

      (write-line "  <Style ss:ID=\"ReportLabel\">" f)
      (write-line "   <Alignment ss:Horizontal=\"Left\" ss:Vertical=\"Center\"/>" f)
      (write-line "   <Borders>" f)
      (write-line "    <Border ss:Position=\"Bottom\" ss:LineStyle=\"Continuous\" ss:Weight=\"1\"/>" f)
      (write-line "    <Border ss:Position=\"Left\" ss:LineStyle=\"Continuous\" ss:Weight=\"2\"/>" f)
      (write-line "    <Border ss:Position=\"Right\" ss:LineStyle=\"Continuous\" ss:Weight=\"1\"/>" f)
      (write-line "    <Border ss:Position=\"Top\" ss:LineStyle=\"Continuous\" ss:Weight=\"1\"/>" f)
      (write-line "   </Borders>" f)
      (write-line "  </Style>" f)

      (write-line "  <Style ss:ID=\"ReportValueRight\">" f)
      (write-line "   <Alignment ss:Horizontal=\"Left\" ss:Vertical=\"Center\"/>" f)
      (write-line "   <Borders>" f)
      (write-line "    <Border ss:Position=\"Bottom\" ss:LineStyle=\"Continuous\" ss:Weight=\"1\"/>" f)
      (write-line "    <Border ss:Position=\"Left\" ss:LineStyle=\"Continuous\" ss:Weight=\"1\"/>" f)
      (write-line "    <Border ss:Position=\"Right\" ss:LineStyle=\"Continuous\" ss:Weight=\"2\"/>" f)
      (write-line "    <Border ss:Position=\"Top\" ss:LineStyle=\"Continuous\" ss:Weight=\"1\"/>" f)
      (write-line "   </Borders>" f)
      (write-line "  </Style>" f)

      (write-line "  <Style ss:ID=\"ReportKpdLabel\">" f)
      (write-line "   <Alignment ss:Horizontal=\"Left\" ss:Vertical=\"Center\"/>" f)
      (write-line "   <Borders>" f)
      (write-line "    <Border ss:Position=\"Bottom\" ss:LineStyle=\"Continuous\" ss:Weight=\"2\"/>" f)
      (write-line "    <Border ss:Position=\"Left\" ss:LineStyle=\"Continuous\" ss:Weight=\"2\"/>" f)
      (write-line "    <Border ss:Position=\"Right\" ss:LineStyle=\"Continuous\" ss:Weight=\"1\"/>" f)
      (write-line "    <Border ss:Position=\"Top\" ss:LineStyle=\"Continuous\" ss:Weight=\"1\"/>" f)
      (write-line "   </Borders>" f)
      (write-line "  </Style>" f)

      (write-line "  <Style ss:ID=\"ReportKpd\">" f)
      (write-line "   <Font ss:Bold=\"1\" ss:Color=\"#FF0000\"/>" f)
      (write-line "   <Alignment ss:Horizontal=\"Left\" ss:Vertical=\"Center\"/>" f)
      (write-line "   <Borders>" f)
      (write-line "    <Border ss:Position=\"Bottom\" ss:LineStyle=\"Continuous\" ss:Weight=\"2\"/>" f)
      (write-line "    <Border ss:Position=\"Left\" ss:LineStyle=\"Continuous\" ss:Weight=\"1\"/>" f)
      (write-line "    <Border ss:Position=\"Right\" ss:LineStyle=\"Continuous\" ss:Weight=\"2\"/>" f)
      (write-line "    <Border ss:Position=\"Top\" ss:LineStyle=\"Continuous\" ss:Weight=\"1\"/>" f)
      (write-line "   </Borders>" f)
      (write-line "  </Style>" f)

      (write-line "  <Style ss:ID=\"SectionTitle\">" f)
      (write-line "   <Font ss:Bold=\"1\" ss:Size=\"12\" ss:Underline=\"Single\" ss:Color=\"#FF0000\"/>" f)
      (write-line "   <Interior ss:Color=\"#D9D9D9\" ss:Pattern=\"Solid\"/>" f)
      (write-line "   <Alignment ss:Horizontal=\"Center\" ss:Vertical=\"Center\"/>" f)
      (write-line "   <Borders>" f)
      (write-line "    <Border ss:Position=\"Bottom\" ss:LineStyle=\"Continuous\" ss:Weight=\"2\"/>" f)
      (write-line "    <Border ss:Position=\"Left\" ss:LineStyle=\"Continuous\" ss:Weight=\"2\"/>" f)
      (write-line "    <Border ss:Position=\"Right\" ss:LineStyle=\"Continuous\" ss:Weight=\"2\"/>" f)
      (write-line "    <Border ss:Position=\"Top\" ss:LineStyle=\"Continuous\" ss:Weight=\"2\"/>" f)
      (write-line "   </Borders>" f)
      (write-line "  </Style>" f)

      (write-line "  <Style ss:ID=\"SkipHeaderLeft\">" f)
      (write-line "   <Font ss:Bold=\"1\"/>" f)
      (write-line "   <Interior ss:Color=\"#D9D9D9\" ss:Pattern=\"Solid\"/>" f)
      (write-line "   <Alignment ss:Horizontal=\"Center\" ss:Vertical=\"Center\"/>" f)
      (write-line "   <Borders>" f)
      (write-line "    <Border ss:Position=\"Bottom\" ss:LineStyle=\"Continuous\" ss:Weight=\"1\"/>" f)
      (write-line "    <Border ss:Position=\"Left\" ss:LineStyle=\"Continuous\" ss:Weight=\"2\"/>" f)
      (write-line "    <Border ss:Position=\"Right\" ss:LineStyle=\"Continuous\" ss:Weight=\"1\"/>" f)
      (write-line "    <Border ss:Position=\"Top\" ss:LineStyle=\"Continuous\" ss:Weight=\"1\"/>" f)
      (write-line "   </Borders>" f)
      (write-line "  </Style>" f)

      (write-line "  <Style ss:ID=\"SkipHeaderMid\">" f)
      (write-line "   <Font ss:Bold=\"1\"/>" f)
      (write-line "   <Interior ss:Color=\"#D9D9D9\" ss:Pattern=\"Solid\"/>" f)
      (write-line "   <Alignment ss:Horizontal=\"Center\" ss:Vertical=\"Center\"/>" f)
      (write-line "   <Borders>" f)
      (write-line "    <Border ss:Position=\"Bottom\" ss:LineStyle=\"Continuous\" ss:Weight=\"1\"/>" f)
      (write-line "    <Border ss:Position=\"Left\" ss:LineStyle=\"Continuous\" ss:Weight=\"1\"/>" f)
      (write-line "    <Border ss:Position=\"Right\" ss:LineStyle=\"Continuous\" ss:Weight=\"1\"/>" f)
      (write-line "    <Border ss:Position=\"Top\" ss:LineStyle=\"Continuous\" ss:Weight=\"1\"/>" f)
      (write-line "   </Borders>" f)
      (write-line "  </Style>" f)

      (write-line "  <Style ss:ID=\"SkipHeaderRight\">" f)
      (write-line "   <Font ss:Bold=\"1\"/>" f)
      (write-line "   <Interior ss:Color=\"#D9D9D9\" ss:Pattern=\"Solid\"/>" f)
      (write-line "   <Alignment ss:Horizontal=\"Center\" ss:Vertical=\"Center\"/>" f)
      (write-line "   <Borders>" f)
      (write-line "    <Border ss:Position=\"Bottom\" ss:LineStyle=\"Continuous\" ss:Weight=\"1\"/>" f)
      (write-line "    <Border ss:Position=\"Left\" ss:LineStyle=\"Continuous\" ss:Weight=\"1\"/>" f)
      (write-line "    <Border ss:Position=\"Right\" ss:LineStyle=\"Continuous\" ss:Weight=\"2\"/>" f)
      (write-line "    <Border ss:Position=\"Top\" ss:LineStyle=\"Continuous\" ss:Weight=\"1\"/>" f)
      (write-line "   </Borders>" f)
      (write-line "  </Style>" f)

      (write-line "  <Style ss:ID=\"SkipDataLeft\">" f)
      (write-line "   <Font ss:Color=\"#FF0000\"/>" f)
      (write-line "   <Alignment ss:Horizontal=\"Center\" ss:Vertical=\"Center\"/>" f)
      (write-line "   <Borders>" f)
      (write-line "    <Border ss:Position=\"Bottom\" ss:LineStyle=\"Continuous\" ss:Weight=\"1\"/>" f)
      (write-line "    <Border ss:Position=\"Left\" ss:LineStyle=\"Continuous\" ss:Weight=\"2\"/>" f)
      (write-line "    <Border ss:Position=\"Right\" ss:LineStyle=\"Continuous\" ss:Weight=\"1\"/>" f)
      (write-line "    <Border ss:Position=\"Top\" ss:LineStyle=\"Continuous\" ss:Weight=\"1\"/>" f)
      (write-line "   </Borders>" f)
      (write-line "  </Style>" f)

      (write-line "  <Style ss:ID=\"SkipDataMid\">" f)
      (write-line "   <Font ss:Color=\"#FF0000\"/>" f)
      (write-line "   <Alignment ss:Horizontal=\"Center\" ss:Vertical=\"Center\"/>" f)
      (write-line "   <Borders>" f)
      (write-line "    <Border ss:Position=\"Bottom\" ss:LineStyle=\"Continuous\" ss:Weight=\"1\"/>" f)
      (write-line "    <Border ss:Position=\"Left\" ss:LineStyle=\"Continuous\" ss:Weight=\"1\"/>" f)
      (write-line "    <Border ss:Position=\"Right\" ss:LineStyle=\"Continuous\" ss:Weight=\"1\"/>" f)
      (write-line "    <Border ss:Position=\"Top\" ss:LineStyle=\"Continuous\" ss:Weight=\"1\"/>" f)
      (write-line "   </Borders>" f)
      (write-line "  </Style>" f)

      (write-line "  <Style ss:ID=\"SkipDataRight\">" f)
      (write-line "   <Font ss:Color=\"#FF0000\"/>" f)
      (write-line "   <Alignment ss:Horizontal=\"Center\" ss:Vertical=\"Center\"/>" f)
      (write-line "   <Borders>" f)
      (write-line "    <Border ss:Position=\"Bottom\" ss:LineStyle=\"Continuous\" ss:Weight=\"1\"/>" f)
      (write-line "    <Border ss:Position=\"Left\" ss:LineStyle=\"Continuous\" ss:Weight=\"1\"/>" f)
      (write-line "    <Border ss:Position=\"Right\" ss:LineStyle=\"Continuous\" ss:Weight=\"2\"/>" f)
      (write-line "    <Border ss:Position=\"Top\" ss:LineStyle=\"Continuous\" ss:Weight=\"1\"/>" f)
      (write-line "   </Borders>" f)
      (write-line "  </Style>" f)

      (write-line "  <Style ss:ID=\"SkipTotal\">" f)
      (write-line "   <Font ss:Bold=\"1\" ss:Color=\"#FF0000\"/>" f)
      (write-line "   <Alignment ss:Horizontal=\"Left\" ss:Vertical=\"Center\"/>" f)
      (write-line "   <Borders>" f)
      (write-line "    <Border ss:Position=\"Bottom\" ss:LineStyle=\"Continuous\" ss:Weight=\"2\"/>" f)
      (write-line "    <Border ss:Position=\"Left\" ss:LineStyle=\"Continuous\" ss:Weight=\"2\"/>" f)
      (write-line "    <Border ss:Position=\"Right\" ss:LineStyle=\"Continuous\" ss:Weight=\"2\"/>" f)
      (write-line "    <Border ss:Position=\"Top\" ss:LineStyle=\"Continuous\" ss:Weight=\"1\"/>" f)
      (write-line "   </Borders>" f)
      (write-line "  </Style>" f)

      (write-line " </Styles>" f)

      (eu-worksheet f "Раскрой")
      (eu-column f "60" "0")
      (eu-column f "200" "1")
      (eu-column f "120" "0")
      (eu-column f "100" "0")
      (eu-column f "120" "0")

      (eu-row-begin f "ss:Height=\"20\"")
      (eu-cell f "Header" "String" "Раскрой хлыстов" "ss:MergeAcross=\"4\"")
      (eu-row-end f)

      (eu-row-begin f "")
      (eu-cell f "Header" "String" "Хлыст" "")
      (eu-cell f "Header" "String" "Детали" "")
      (eu-cell f "Header" "String" "Использовано" "")
      (eu-cell f "Header" "String" "Отход" "")
      (eu-cell f "Header" "String" "Использование_%" "")
      (eu-row-end f)

      (setq i 0)
      (foreach bar bars
        (setq i (1+ i))
        (setq pieces (cdr bar) waste (car bar) used (- stock waste)
              util (* 100.0 (/ used stock)))
        (eu-row-begin f "")
        (eu-cell f "Data" "Number" (itoa i) "")
        (eu-cell f "Data" "String" (n1-list-to-str pieces " + ") "")
        (eu-cell f "Data" "Number" (rtos used 2 1) "")
        (eu-cell f "Data" "Number" (rtos waste 2 1) "")
        (eu-cell f "Data" "Number" (rtos util 2 1) "")
        (eu-row-end f))

      (eu-row-begin f "")
      (eu-cell f "" "String" "" "")
      (eu-row-end f)

      (eu-row-begin f "")
      (eu-cell-skip f 1)
      (eu-cell f "ReportTitle" "String" "ОТЧЕТ" "ss:MergeAcross=\"2\"")
      (eu-row-end f)

      (eu-row-begin f "")
      (eu-cell-skip f 1)
      (eu-cell f "ReportLabel" "String" "Длина хлыста (заготовка):" "")
      (eu-cell f "ReportValueRight" "String" (strcat (itoa (fix stock)) " мм") "ss:MergeAcross=\"1\"")
      (eu-row-end f)

      (setq total-cnt 0 total-product-mm 0.0)
      (foreach bar bars
        (foreach p (cdr bar)
          (setq total-cnt (1+ total-cnt))
          (setq total-product-mm (+ total-product-mm p))))

      (eu-row-begin f "")
      (eu-cell-skip f 1)
      (eu-cell f "ReportLabel" "String" "Всего изделий:" "")
      (eu-cell f "ReportValueRight" "String" (strcat (itoa total-cnt) " шт") "ss:MergeAcross=\"1\"")
      (eu-row-end f)

      (eu-row-begin f "")
      (eu-cell-skip f 1)
      (eu-cell f "ReportLabel" "String" "Суммарная длина:" "")
      (eu-cell f "ReportValueRight" "String" (strcat (rtos (/ product-total-mm 1000.0) 2 2) " м.п.") "ss:MergeAcross=\"1\"")
      (eu-row-end f)

      (eu-row-begin f "")
      (eu-cell-skip f 1)
      (eu-cell f "ReportLabel" "String" "Хлыстов:" "")
      (eu-cell f "ReportValueRight" "String" (strcat (itoa num-bars) " шт") "ss:MergeAcross=\"1\"")
      (eu-row-end f)

      (eu-row-begin f "")
      (eu-cell-skip f 1)
      (eu-cell f "ReportLabel" "String" "Общая длина хлыстов:" "")
      (eu-cell f "ReportValueRight" "String" (strcat (rtos (/ stock-total-mm 1000.0) 2 2) " м.п.") "ss:MergeAcross=\"1\"")
      (eu-row-end f)

      (eu-row-begin f "")
      (eu-cell-skip f 1)
      (eu-cell f "ReportKpdLabel" "String" "КПД использования:" "")
      (eu-cell f "ReportKpd" "String" (strcat (rtos kpd 2 1) " %") "ss:MergeAcross=\"1\"")
      (eu-row-end f)

      ;; ------------------------------------------------------
      ;; ПЕРЕЧЕНЬ ИЗДЕЛИЙ - те же строки, что в таблице AutoCAD:
      ;; n1-piece-rows даёт строку на каждую марку, изделия без марки
      ;; идут отдельной строкой с прочерком. Решатель уже отработал,
      ;; на раскрой раздел не влияет. Колонка «Марка» появляется только
      ;; при наличии марок - без них состав файла прежний.
      ;; ------------------------------------------------------
      (setq hasMarks nil)
      (foreach rec all-pieces
        (if (n1-marks-for (car rec)) (setq hasMarks T)))
      (if all-pieces
        (progn
          (eu-row-begin f "")
          (eu-cell f "" "String" "" "")
          (eu-row-end f)

          (eu-row-begin f "")
          (eu-cell-skip f 1)
          (eu-cell f "SectionTitle" "String" "ПЕРЕЧЕНЬ ИЗДЕЛИЙ"
                   (if hasMarks "ss:MergeAcross=\"3\"" "ss:MergeAcross=\"2\""))
          (eu-row-end f)

          (eu-row-begin f "")
          (eu-cell-skip f 1)
          (eu-cell f "SkipHeaderLeft" "String" "Длина, мм" "")
          (if hasMarks (eu-cell f "SkipHeaderMid" "String" "Марка" ""))
          (eu-cell f "SkipHeaderMid" "String" "Кол-во, шт" "")
          (eu-cell f "SkipHeaderRight" "String" "Сумма, м.п." "")
          (eu-row-end f)

          (setq rows (n1-piece-rows
                       (vl-sort all-pieces '(lambda (a b) (> (car a) (car b))))))
          (foreach rw rows
            (eu-row-begin f "")
            (eu-cell-skip f 1)
            (eu-cell f "SkipDataLeft" "Number" (itoa (fix (car rw))) "")
            (if hasMarks (eu-cell f "SkipDataMid" "String" (caddr rw) ""))
            (eu-cell f "SkipDataMid" "Number" (itoa (cadr rw)) "")
            (eu-cell f "SkipDataRight" "Number"
                     (rtos (/ (* (car rw) (cadr rw)) 1000.0) 2 2) "")
            (eu-row-end f))
        )
      )

      (if oversized
        (progn
          (eu-row-begin f "")
          (eu-cell f "" "String" "" "")
          (eu-row-end f)

          (eu-row-begin f "")
          (eu-cell-skip f 1)
          (eu-cell f "SectionTitle" "String" "НЕРАЗМЕЩЕННЫЕ ДЕТАЛИ (длиннее хлыста)" "ss:MergeAcross=\"2\"")
          (eu-row-end f)

          (eu-row-begin f "")
          (eu-cell-skip f 1)
          (eu-cell f "SkipHeaderLeft" "String" "Длина, мм" "")
          (eu-cell f "SkipHeaderMid" "String" "Кол-во, шт" "")
          (eu-cell f "SkipHeaderRight" "String" "Сумма, м.п." "")
          (eu-row-end f)

          (foreach rec oversized
            (eu-row-begin f "")
            (eu-cell-skip f 1)
            (eu-cell f "SkipDataLeft" "Number" (itoa (fix (car rec))) "")
            (eu-cell f "SkipDataMid" "Number" (itoa (cadr rec)) "")
            (eu-cell f "SkipDataRight" "Number" (rtos (/ (* (car rec) (cadr rec)) 1000.0) 2 2) "")
            (eu-row-end f))

          (eu-row-begin f "")
          (eu-cell-skip f 1)
          (eu-cell f "SkipTotal" "String" (strcat "Всего неразмещенных: "
                                                  (itoa total-cnt-unplaced) " шт, "
                                                  (rtos total-sum-unplaced 2 2) " м.п.")
                   "ss:MergeAcross=\"2\"")
          (eu-row-end f)))

      (eu-worksheet-end f)
      (eu-doc-end f)
      (close f)
      (princ (strcat "\nXLS сохранен: " fname))
      T
    )
  )
)

;; ---------- CSV-экспорт (fallback) ----------
(defun n1-write-csv (bars stock kerf oversized all-pieces /
                       fname f i bar pieces waste used util rec
                       total-cnt-unplaced total-sum-unplaced
                       hasMarks rows rw)
  (setq fname (strcat (getvar "DWGPREFIX")
                      (vl-filename-base (getvar "DWGNAME"))
                      " Раскрой хлыстов.csv"))
  (setq f (open fname "w"))
  (if f
    (progn
      (write-line "Хлыст;Детали;Использовано;Отход;Использование_%" f)
      (setq i 0)
      (foreach bar bars
        (setq i (1+ i))
        (setq pieces (cdr bar) waste (car bar) used (- stock waste)
              util (* 100.0 (/ used stock)))
        (write-line (strcat (itoa i) ";" (n1-list-to-str pieces " + ") ";"
                            (rtos used 2 1) ";" (rtos waste 2 1) ";"
                            (rtos util 2 1)) f)
      )
      ;; Перечень изделий - тот же состав строк, что в XLS и в таблице
      ;; AutoCAD. Точка с запятой внутри марки заменяется запятой, чтобы
      ;; не ломать разделитель CSV.
      (setq hasMarks nil)
      (foreach rec all-pieces
        (if (n1-marks-for (car rec)) (setq hasMarks T)))
      (if all-pieces
        (progn
          (write-line "" f)
          (write-line "ПЕРЕЧЕНЬ ИЗДЕЛИЙ" f)
          (write-line (if hasMarks
                        "Длина, мм;Марка;Кол-во, шт;Сумма, м.п."
                        "Длина, мм;Кол-во, шт;Сумма, м.п.") f)
          (setq rows (n1-piece-rows
                       (vl-sort all-pieces '(lambda (a b) (> (car a) (car b))))))
          (foreach rw rows
            (write-line
              (strcat (itoa (fix (car rw))) ";"
                      (if hasMarks
                        (strcat (vl-string-translate ";" "," (caddr rw)) ";")
                        "")
                      (itoa (cadr rw)) ";"
                      (vl-string-translate "." ","
                        (rtos (/ (* (car rw) (cadr rw)) 1000.0) 2 2))) f))
        )
      )
      (if oversized
        (progn
          (setq oversized (vl-sort oversized '(lambda (a b) (> (car a) (car b)))))

          (setq total-cnt-unplaced 0 total-sum-unplaced 0.0)
          (foreach rec oversized
            (setq total-cnt-unplaced (+ total-cnt-unplaced (cadr rec)))
            (setq total-sum-unplaced (+ total-sum-unplaced
                                        (/ (* (car rec) (cadr rec)) 1000.0)))
          )
          (write-line "" f)
          (write-line "НЕРАЗМЕЩЕННЫЕ ДЕТАЛИ (длиннее хлыста)" f)
          (write-line "Длина, мм;Кол-во, шт;Сумма, м.п." f)
          (foreach rec oversized
            (write-line
              (strcat (itoa (fix (car rec))) ";" (itoa (cadr rec)) ";"
                      (vl-string-translate "." ","
                        (rtos (/ (* (car rec) (cadr rec)) 1000.0) 2 2))) f)
          )
          (write-line (strcat "Всего;" (itoa total-cnt-unplaced) ";"
                              (vl-string-translate "." ","
                                (rtos total-sum-unplaced 2 2))) f)
        )
      )
      (close f)
      (princ (strcat "\nCSV сохранен: " fname))
      T
    )
    nil
  )
)

;; ============================================================
;; Главная функция
;; ============================================================
(defun cutline-main (layers-from-caller / *error* ss tol stock kerf insPt
                       pieces pieces-ok pieces-oversized split
                       sorted bars
                       bbox0 bbox1 bbox2 bbox3 bbox-frame bbox p1 p2 color-map
                       barHeight sumInsPt num-bars stock-total-mm
                       total-cnt total-product-mm kpd rec blockName baseName
                       lastEnt ssNew ent oldEcho doc uMark
                       blkRefsSet blkRefsBeforeSet blkRefsBefore blkIdx blkRefsAfter blkCmdResult
                       layers layers-str total-input type-counts
                       user-filter line-cnt mline-cnt dynblock-cnt
                       dynblock-type mline-type
                       export-xls export-acad
                       default-xls default-acad
                       default-stock default-kerf
                       dialog-result r xls-ok
                       old-transparency-display svSaved v5ans
                       pfCount oldPickfirst blkExpected blkTally
                       blkObjCount blkTypes ssNewCount blkGuard wrapMark)
  (defun *error* (msg)
    (if (and msg (not (wcmatch (strcase msg) "*CANCEL*,*QUIT*,*BREAK*,*EXIT*")))
      (princ (strcat "\n[CUTLINE ERROR] " msg)))
    (if uMark (tu-undo-end doc))
    (tu-sysvar-restore svSaved)
    (princ))
  

  ;; V8: guard - любой обрыв вернёт исходные значения через *error*
  (setq svSaved (tu-sysvar-save (list "CMDECHO")))
  (if (= (type ae-settings-output) 'SUBR)
    (setq *CUTLINE-FRAME-LAYER*
      (ae-settings-output 'CUTLINE "output.frame.layer"
        *CUTLINE-FRAME-LAYER*)))

  (princ "\n=== Линейный раскрой мерного материала ===")

  (if (eq layers-from-caller 'ASK)
    (progn
      (setq layers-str (getstring T "\nВведите слои через запятую (Enter — все слои): "))
      (if (/= layers-str "")
        (setq layers (mapcar '(lambda (x) (vl-string-trim " " x))
                             (n1-split-string layers-str ",")))
        (setq layers nil)
      )
    )
    (setq layers layers-from-caller)
  )

  (princ (strcat "\n" (car (n1-layer-display-list layers))))

  (princ "\nВыберите объекты — исходные детали:")
  (princ "\n(принимаются LINE, MLINE и динамические блоки с длиной)")
  (princ "\n(если объекты уже выделены — Enter)")

  (setq ss (su-select-cutline-objects layers))

  (if (null ss)
    (progn (princ "\nНичего не выбрано.") (princ) (exit)))

  (setq total-input (sslength ss))
  (princ (strcat "\nВыбрано объектов: " (itoa total-input)))

  ;; Этап 2 (V5): мягкий лимит - предупреждение (GUI + командная строка)
  ;; и запрос на продолжение; Нет/Enter = остановка (прежнее поведение).
  (if (> total-input *n1-max-parts*)
    (progn
      (princ (strcat "\n[CUTLINE][GUARD] Обнаружено " (itoa total-input)
                      " деталей при лимите " (itoa *n1-max-parts*)
                      ". Проверьте выборку/слои."))
      (alert (strcat "AutoExtraction / CUTLINE\n\nВ выборке "
                     (itoa total-input) " объектов при лимите "
                     (itoa *n1-max-parts*) ".\nОбработка может занять очень долгое время.\n\nРешение - в командной строке."))
      (initget "Да Нет _Yes No")
      (setq v5ans (getkword "\nПродолжить обработку несмотря на лимит? [Да/Нет] <Нет>: "))
      (if (= v5ans "Yes")
        (princ "\n[CUTLINE][GUARD] Продолжаю обработку по явному подтверждению.")
        (progn
          (princ "\n[CUTLINE][GUARD] Обработка остановлена пользователем.")
          (princ) (exit)))))
  (tu-diag "SCAN" (strcat "объектов в выборке: " (itoa total-input)))

  (setq type-counts (n1-count-by-type ss))
  (n1-print-type-counts type-counts)

  (setq line-cnt     (cdr (assoc "LINE" type-counts)))
  (setq mline-cnt    (cdr (assoc "MLINE" type-counts)))
  (setq dynblock-cnt (cdr (assoc "DYNBLOCK" type-counts)))
  (if (null line-cnt)     (setq line-cnt 0))
  (if (null mline-cnt)    (setq mline-cnt 0))
  (if (null dynblock-cnt) (setq dynblock-cnt 0))

  (if (and (= line-cnt 0) (= mline-cnt 0) (= dynblock-cnt 0))
    (progn
      (princ "\nНет объектов подходящих типов.")
      (princ) (exit)
    )
  )

  (setq default-stock *CUTLINE-LAST-STOCK*)
  (setq default-kerf  *CUTLINE-LAST-KERF*)
  (setq default-xls   *CUTLINE-LAST-XLS*)
  (setq default-acad  *CUTLINE-LAST-ACAD*)

  (if (not (eq layers-from-caller 'ASK))
    (progn
      (if (boundp '*CUTLINE-CREATE-XLS*)
        (setq default-xls *CUTLINE-CREATE-XLS*))
      (if (boundp '*CUTLINE-CREATE-TABLE*)
        (setq default-acad *CUTLINE-CREATE-TABLE*))
    )
  )

  (setq tol *CUTLINE-DEFAULT-TOL*)

  (setq r (vl-catch-all-apply
            'n1-cutline-dialog
            (list line-cnt mline-cnt dynblock-cnt ss *CUTLINE-DEFAULT-TOL*
                  default-stock default-kerf layers default-xls default-acad)))

  (cond
    ((vl-catch-all-error-p r)
     (princ (strcat "\nОшибка диалога: " (vl-catch-all-error-message r)))
     (princ "\nРаскрой отменен.")
     (princ) (exit)
    )
    ((null r)
     (princ "\nРаскрой отменен пользователем.")
     (princ) (exit)
    )
    (T (setq dialog-result r))
  )

  (setq user-filter   (car dialog-result)
        tol           (cadr dialog-result)
        stock         (caddr dialog-result)
        kerf          (cadddr dialog-result)
        export-xls    (nth 4 dialog-result)
        export-acad   (nth 5 dialog-result)
        dynblock-type (nth 6 dialog-result)
        mline-type    (nth 7 dialog-result))

  (setq *CUTLINE-LAST-STOCK* stock
        *CUTLINE-LAST-KERF*  kerf
        *CUTLINE-LAST-XLS*   export-xls
        *CUTLINE-LAST-ACAD*  export-acad)

  (princ "\nПараметры приняты из окна диалога.")

  (cond
    ((eq user-filter 'LINE)
     (setq ss (n1-filter-ss-by-type ss "LINE"))
     (princ "\nОставлены только линии (LINE)."))
    ((eq user-filter 'MLINE)
     (setq ss (n1-filter-ss-by-mline-type ss mline-type))
     (if (and mline-type (/= mline-type ""))
       (princ (strcat "\nОставлены мультилинии стиля: " mline-type))
       (princ "\nОставлены все мультилинии."))
    )
    ((eq user-filter 'DYNBLOCK)
     (setq ss (n1-filter-ss-by-type-and-name ss "DYNBLOCK" dynblock-type))
     (if (and dynblock-type (/= dynblock-type "") (/= dynblock-type "Все типы блоков"))
       (princ (strcat "\nОставлены динамические блоки типа: " dynblock-type))
       (princ "\nОставлены все динамические блоки."))
    )
    (T (princ "\nОставлены линии, мультилинии и динамические блоки."))
  )

  (if (= (sslength ss) 0)
    (progn (princ "\nПосле фильтрации не осталось объектов.") (princ) (exit)))

  (setq type-counts (n1-count-by-type ss))
  (n1-print-type-counts type-counts)

  (princ (strcat "\nПараметры: допуск " (rtos tol 2 2)
                 " мм, хлыст " (rtos stock 2 0)
                 " мм, рез " (rtos kerf 2 2) " мм."))
  (princ (strcat "\nЭкспорт: "
                 (if export-xls  ".xls" "без .xls") ", "
                 (if export-acad "таблица AutoCAD" "без таблицы")))

  (setq pieces (n1-extract-pieces ss tol
                                  *CUTLINE-MIN-LENGTH* *CUTLINE-MAX-LENGTH*))
  (if (null pieces)
    (progn (princ "\nНе удалось извлечь длины.") (princ) (exit)))
  (tu-diag "FILTER" (strcat "групп длин: " (itoa (length pieces))))

  (setq total-cnt 0)
  (foreach rec pieces (setq total-cnt (+ total-cnt (cadr rec))))
  (princ (strcat "\nВсего деталей: " (itoa (length pieces))
                 ", общее количество: " (itoa total-cnt)))

  (setq split (n1-split-by-stock pieces stock))
  (setq pieces-ok (car split) pieces-oversized (cadr split))

  (n1-report-oversized pieces-oversized stock)

  (if (null pieces-ok)
    (progn
      (princ "\nВсе детали превышают длину хлыста. Раскрой невозможен.")
      (princ) (exit)
    )
  )

  (pu-begin "CUTLINE:expand")
  (setq sorted (n1-expand pieces-ok))
  (pu-end "CUTLINE:expand")
  (pu-begin "CUTLINE:ffd")
  (setq bars (n1-ffd sorted stock kerf))
  (pu-end "CUTLINE:ffd")
  (tu-diag "PACK" (strcat "хлыстов: " (itoa (length bars))))
  (n1-report bars stock kerf)

  (setq num-bars (length bars))
  (setq stock-total-mm (* num-bars stock))
  (setq total-cnt 0 total-product-mm 0.0)
  (foreach rec pieces-ok
    (setq total-cnt (+ total-cnt (cadr rec)))
    (setq total-product-mm (+ total-product-mm (* (car rec) (cadr rec))))
  )
  (setq kpd (if (> stock-total-mm 0)
              (* 100.0 (/ total-product-mm stock-total-mm)) 0.0))
  (princ (strcat "\nВсего изделий: " (itoa total-cnt)
                 " шт, суммарная длина "
                 (rtos (/ total-product-mm 1000.0) 2 2) " м.п."))
  (princ (strcat "\nХлыстов: " (itoa num-bars)
                 " шт, общая длина "
                 (rtos (/ stock-total-mm 1000.0) 2 2) " м.п."))
  (princ (strcat "\nКПД использования: " (rtos kpd 2 1) " %"))

  (if export-xls
    (progn
      (pu-begin "CUTLINE:xls")
      (setq xls-ok
        (n1-write-xls bars stock kerf pieces-oversized
                      num-bars stock-total-mm total-product-mm kpd pieces-ok))
      (pu-end "CUTLINE:xls")
      (if (not xls-ok)
        (progn
          (princ "\nНе удалось создать XLS. Сохраняю CSV...")
          (n1-write-csv bars stock kerf pieces-oversized pieces-ok)
        )
      )
    )
    (princ "\nГалочка .xls снята — файл не создается.")
  )

  (if export-acad
    (progn
      (setq insPt (getpoint "\nУкажите точку вставки раскладки: "))
      (if insPt
        (progn
          (setq old-transparency-display (getvar "TRANSPARENCYDISPLAY"))
          (n1-enable-transparency-display)

          (n1-ensure-italic-style)
          (setq color-map (n1-build-color-map pieces-ok))
          (setq baseName (vl-filename-base (getvar "DWGNAME")))
          (setq blockName
            (n1-unique-block-name
              (if (= (type ae-settings-expand-output-template) 'SUBR)
                (ae-settings-expand-output-template 'CUTLINE)
                (strcat "Раскрой " baseName))))

          (setq doc (vl-catch-all-apply 'vla-get-ActiveDocument
                                        (list (vlax-get-acad-object))))
          (if (and (not (vl-catch-all-error-p doc)) doc)
            (progn
              (tu-undo-begin)
              (setq uMark T)
            )
          )

          (setq lastEnt (entlast))

          ;; Ред. 16: своя undo-метка на отрисовку+упаковку раскладки и сброс
          ;; учёта созданных объектов (набор для блока строится из него).
          (setq *n1-created* '())
          (setq *n1-created-miss* 0)
          (setq wrapMark (n1-wrap-mark-begin doc))
          (princ (strcat "\n[CUTLINE][STEP] отрисовка раскладки: старт ("
                         (n1-safe-str (if wrapMark "метка UNDO открыта"
                                          "метка UNDO недоступна")) ")"))

          ;; ШАПКА КАРТЫ РАСКРОЯ (над первым хлыстом)
          (pu-begin "CUTLINE:draw-header")
          (setq bbox0 (n1-draw-header insPt stock kerf))
          (pu-end "CUTLINE:draw-header")

          ;; Раскладка хлыстов
          (pu-begin "CUTLINE:draw-layout")
          (setq bbox1 (n1-draw-layout bars stock kerf insPt color-map))
          (pu-end "CUTLINE:draw-layout")
          (setq barHeight (/ stock 30.0))

          ;; РАМКА вокруг шапки и хлыстов (без таблиц)
          (pu-begin "CUTLINE:draw-frame")
          (setq bbox-frame (n1-draw-frame (n1-combine-bbox bbox0 bbox1)))
          (pu-end "CUTLINE:draw-frame")

          ;; Таблицы сдвинуты правее рамки, чтобы не пересекаться
          (setq sumInsPt (list (+ (car (cadr bbox-frame)) (* barHeight 2.0))
                               (cadr (cadr bbox-frame))))
          (setq bbox2 (n1-draw-summary bars pieces-ok stock sumInsPt color-map
                                        pieces-oversized))
          (setq bbox3
            (if pieces-oversized
              (n1-draw-oversized pieces-oversized stock
                (list (car (car bbox2))
                      (- (cadr (car bbox2)) (* barHeight 2.0))))
              nil))
          (princ "\n[CUTLINE][STEP] отрисовка раскладки: готово (шапка, хлысты, рамка, таблицы)")

          ;; Ред. 16: только объекты, созданные отрисовкой (*n1-created*).
          ;; Обход базы entnext затягивал в блок посторонние объекты чертежа:
          ;; атрибуты и вставки иных пространств/определений (диагностика ниже,
          ;; только чтение и печать).
          (setq ssNew (ssadd))
          (foreach ent *n1-created*
            (if (entget ent) (ssadd ent ssNew)))
          (setq ssNewCount (sslength ssNew))
          (princ (strcat "\n[CUTLINE][STEP] набор для блока: "
                         (itoa ssNewCount) " объектов раскладки"
                         (if (> *n1-created-miss* 0)
                           (strcat ", НЕ отслежено: "
                                   (itoa *n1-created-miss*))
                           "")))
          (vl-catch-all-apply (function n1-scan-foreign-entities)
                              (list lastEnt ssNew))
          (princ "\n[CUTLINE][STEP] диагностика цепочки БД: завершена")

          (princ "\nCUTLINE: упаковка раскладки в блок...")
          (pu-begin "CUTLINE:wrap-block")
          (if (> (sslength ssNew) 0)
            (progn
              (setq oldEcho (getvar "CMDECHO"))
              (setvar "CMDECHO" 0)
              ;; Число INSERT с этим именем ДО -BLOCK (защита от двойного INSERT, Шаг 4):
              ;; в версиях AutoCAD, где -BLOCK спрашивает [Преобразовать/Удалить],
              ;; ENTER выбирает «Преобразовать» и INSERT создается самим -BLOCK.
              (pu-begin "CUTLINE:wrap:ssget")
              (setq blkRefsSet (ssget "_X" (list '(0 . "INSERT") (cons 2 blockName))))
              (setq blkRefsBeforeSet blkRefsSet)
              (pu-end "CUTLINE:wrap:ssget")
              (setq blkRefsBefore (if blkRefsSet (sslength blkRefsSet) 0))
              ;; Ред. 15: предвыделение недопустимо — -BLOCK добавляет
              ;; выделенные объекты к набору и уносит их в блок раскладки.
              (setq pfCount (n1-clear-pickfirst nil))
              (setq oldPickfirst (getvar "PICKFIRST"))
              (vl-catch-all-apply 'setvar (list "PICKFIRST" 0))
              (setq blkExpected (n1-ss-type-tally ssNew))
              (pu-begin "CUTLINE:wrap:block")
              (setq blkCmdResult
                    (vl-catch-all-apply 'vl-cmdf
                      (list "_.-BLOCK" blockName insPt ssNew "")))
              (pu-end "CUTLINE:wrap:block")
              (setvar "CMDECHO" oldEcho)
              (vl-catch-all-apply 'setvar (list "PICKFIRST" oldPickfirst))
              (cond
                ((vl-catch-all-error-p blkCmdResult)
                 (princ (strcat "\nОшибка при создании блока: "
                                (vl-catch-all-error-message blkCmdResult))))
                ((not (tblsearch "BLOCK" blockName))
                 (princ "\nНе удалось создать блок."))
                (T
                 (progn
                  (setq blkRefsSet (ssget "_X" (list '(0 . "INSERT") (cons 2 blockName))))
                  (setq blkRefsAfter (if blkRefsSet (sslength blkRefsSet) 0))
                  (if (= (type ae-settings-output-layer) 'SUBR)
                    (n1-apply-new-block-ref-layers
                      blkRefsBeforeSet blkRefsSet
                      (ae-settings-output-layer 'CUTLINE)))
                  (cond
                    ((= blkRefsAfter (1+ blkRefsBefore))
                     ;; Ровно один новый INSERT — его создал сам -BLOCK (Шаг 4), второй не нужен.
                     (princ (strcat "\nСоздан блок с раскладкой: " blockName
                                    " (INSERT создан самим -BLOCK, ровно 1)")))
                    ((> blkRefsAfter (1+ blkRefsBefore))
                     (princ (strcat "\nСоздан блок с раскладкой: " blockName
                                    "\nВНИМАНИЕ: после -BLOCK новых INSERT: " (itoa (- blkRefsAfter blkRefsBefore))
                                    " (ожидался 1) — повторная вставка отменена.")))
                    (T
(progn
                      ;; INSERT не создан: стираем оригиналы, пережившие -BLOCK
                      ;; (режим «оставить»), и вставляем ровно один INSERT.
                      (setq blkIdx 0)
                      (repeat (sslength ssNew)
                        (setq ent (ssname ssNew blkIdx))
                        (if (entget ent) (entdel ent))
                        (setq blkIdx (1+ blkIdx)))
                      (n1-block-insert blockName insPt)
                      (tu-diag "BLOCK" (strcat "блок вставлен: " blockName))
                      ;; Контроль (Шаг 4): должен остаться ровно один новый INSERT
                      (setq blkRefsSet (ssget "_X" (list '(0 . "INSERT") (cons 2 blockName))))
                      (setq blkRefsAfter (if blkRefsSet (sslength blkRefsSet) 0))
                      (princ (strcat "\nСоздан блок с раскладкой: " blockName
                                     " (ссылок до: " (itoa blkRefsBefore)
                                     ", после: " (itoa blkRefsAfter) ")"
                                     (if (= blkRefsAfter (1+ blkRefsBefore))
                                       ""
                                       " (ВНИМАНИЕ: прирост не равен 1!)")))))))))
            )
            (princ "\nНет объектов для создания блока.")
          )
          (pu-end "CUTLINE:wrap-block")

          ;; Ред. 15: контроль состава. В блоке должны быть ТОЛЬКО объекты
          ;; раскладки; посторонние (предвыделение) = потеря объектов чертежа.
          (if (and (not blkGuard) (tblsearch "BLOCK" blockName))
            (progn
              (setq blkTally
                (vl-catch-all-apply (function n1-block-type-tally)
                                    (list blockName)))
              (if (vl-catch-all-error-p blkTally) (setq blkTally nil))
              (if blkTally
                (progn
                  (setq blkObjCount (car blkTally)
                        blkTypes   (cdr blkTally))
                  (princ (strcat "\n[CUTLINE] В блоке объектов: "
                                 (itoa blkObjCount)
                                 " (раскладка: " (itoa ssNewCount) ") — "
                                 (n1-tally-str blkTypes)))
                  (if (/= blkObjCount ssNewCount)
                    ;; Число объектов в блоке не совпало с нарисованным:
                    ;; больше — -BLOCK забрал посторонние (предвыделение),
                    ;; меньше — часть раскладки в блок не попала. И то и другое
                    ;; портит результат, поэтому раскладку откатываем.
                    (progn
                      (setq blkGuard T)
                      (princ (strcat "\n[CUTLINE][GUARD] В блоке объектов "
                                     (itoa blkObjCount) " вместо "
                                     (itoa ssNewCount) ": "
                                     (if (> blkObjCount ssNewCount)
                                       "в блок забраны посторонние объекты."
                                       "часть объектов раскладки в блок не попала.")))
                      (princ (strcat "\n[CUTLINE][GUARD] Состав блока: "
                                     (n1-tally-str blkTypes)))
                      (princ (strcat "\n[CUTLINE][GUARD] Ожидался состав: "
                                     (n1-tally-str blkExpected)))
                      (princ (strcat "\n[CUTLINE][GUARD] Раскладка откатывается ("
                                     blockName
                                     "); объекты чертежа возвращаются на место."))
                      ;; откат делает ветка blkGuard ниже (своя метка)
                    )
                    (if (not (n1-tally-equal-p blkTypes blkExpected))
                      (princ (strcat "\n[CUTLINE] ВНИМАНИЕ: состав блока отличается от раскладки: "
                                     (n1-tally-str blkTypes)))
                    )
                  )
                )
              )
            )
          )

          (if blkGuard
            (progn
              (n1-clear-pickfirst T)
              (n1-disable-transparency-display old-transparency-display)
              ;; Ред. 16: откат всей группы раскладки (метка открыта до отрисовки)
              (n1-wrap-mark-end doc nil)
              (setq wrapMark nil)
              (if uMark (progn (tu-undo-end doc) (setq uMark nil)))
              (setq blkRefsSet (ssget "_X" (list '(0 . "INSERT") (cons 2 blockName))))
              (if (and blkRefsSet (> (sslength blkRefsSet) 0))
                (princ "\n[CUTLINE][GUARD] Автооткат не удался — удалите блок раскроя и выполните UNDO вручную.")
                (princ "\n[CUTLINE] Раскладка откатана: чертёж не изменён.")
              )
              (princ "\n[CUTLINE] Запустите раскрой повторно.")
              (princ)
              (exit)
            )
          )

          ;; Ред. 16: раскладка построена и упакована — закрываем свою метку
          (if wrapMark
            (progn (n1-wrap-mark-end doc T) (setq wrapMark nil))
          )

          ;; Объединяем bbox: рамка (уже включает шапку и хлысты) + таблицы
          (setq bbox (n1-combine-bbox bbox-frame
                        (if bbox3 (n1-combine-bbox bbox2 bbox3) bbox2)))
          (setq p1 (vlax-3d-point (list (car (car bbox)) (cadr (car bbox)) 0.0)))
          (setq p2 (vlax-3d-point (list (car (cadr bbox)) (cadr (cadr bbox)) 0.0)))
          (vl-catch-all-apply 'vla-ZoomWindow (list (vlax-get-acad-object) p1 p2))

          (if (and uMark doc)
            (progn
              (tu-undo-end doc)
              (setq uMark nil)
            )
          )

          ;; Ред. 15: не оставляем пользователю подсвеченное выделение
          (n1-clear-pickfirst T)

          (n1-disable-transparency-display old-transparency-display)
        )
        (princ "\nРаскладка пропущена.")
      )
    )
    (princ "\nГалочка Таблица AutoCAD снята — раскладка не строится.")
  )

  (princ)
)

;; ============================================================
;; Автономные команды
;; ============================================================
(defun c:cutline ( / uDoc r)
  ;; V13: «всё или ничего» - падение/отмена в середине откатывает всю раскладку
  (setq uDoc (tu-undo-begin))
  (setq r (vl-catch-all-apply 'cutline-main (list 'ASK)))
  (grtext -1 "") ;; П3: очистить прогресс (и при откате по ESC тоже)
  (if (vl-catch-all-error-p r)
    (progn
      (tu-undo-cancel uDoc)
      (princ (strcat "\n[CUTLINE] Операция прервана и откачена: "
                     (vl-catch-all-error-message r))))
    (tu-undo-end uDoc))
  (princ))
(defun c:РАСКРОЙХЛЫСТА () (c:cutline))

;; CUTLINE.LSP загружен (ред. 26: длина блока — по маскам свойства из настроек; перечень изделий и марки в XLS и CSV; марка в одну строку с длиной; перечень изделий — строка на каждую марку; подписи детали не наползают; марки в перечне изделий и в углу детали; заголовок «Выбранные слои» со счётчиком; в блок идёт только раскладка; диагностика не роняет раскрой, пошаговые метки; фильтры слоёв Мои/Фасады/Витражи/Окна; U2, П1-П3, V5, V4). Команды: CUTLINE, РАСКРОЙХЛЫСТА
(if (member (ae-reload-sym-type 'ae-banner-add) '(SUBR USUBR))
  (ae-banner-add "CUTLINE" '(
      ("CUTLINE / РАСКРОЙХЛЫСТА" "раскрой хлыста: перечень изделий и марки" "26"))))
(princ)
