;;; ============================================================
;;; help.lsp — расширенная справка AutoExtraction
;;; ============================================================
(vl-load-com)

(setq *AE-HELP-LINES*
  (list
    "AutoExtraction — расширенная справка"
    ""
    "1. НАЗНАЧЕНИЕ"
    "Программа собирает сведения из текущего чертежа и формирует отчеты,"
    "таблицы AutoCAD, файлы XLS/TXT и карты раскроя."
    "Настройки определяют, какие слои и блоки участвуют в работе,"
    "а также куда и под каким именем помещается результат."
    ""
    "2. БЫСТРЫЙ ПОРЯДОК РАБОТЫ"
    "1) Выберите нужные слои в списке Слои."
    "2) При необходимости найдите и выберите блок в панели Блоки."
    "3) Выберите задачу: Фасонка, Подсистема, Облицовка, Витраж или Заполнение."
    "4) Выберите Подробный или Краткий режим отчета."
    "5) Отметьте нужные варианты вывода: XLS, TXT и/или AutoCAD."
    "6) Нажмите Сохранить. Для карт используйте одну из кнопок Раскрой."
    ""
    "3. ГЛАВНОЕ ОКНО"
    "Слои"
    "Выберите один или несколько слоев, на которых расположены исходные данные."
    "Если ничего не выбрано, программа просматривает все доступные слои."
    "Поле Поиск над списком сужает список по маске — см. ниже."
    ""
    "Блоки"
    "Поле Поиск отбирает названия после нажатия Enter."
    "Выберите нужный блок и при необходимости используйте Копия, Вставить или Имя."
    "Эти кнопки работают с выбранным блоком и не меняют правила отчетов."
    ""
    "Поиск в панелях Слои и Блоки"
    "Поле Поиск отбирает список по нажатию Enter. Пустое поле — весь список."
    "Если в запросе нет знаков * ? # @, ищется ВХОЖДЕНИЕ: запрос подс находит"
    "Подсистема, Подсистема алюминиевая и Подсистема оцинкованная."
    "Если хотя бы один такой знак есть, запрос работает как маска и должен"
    "описывать имя ЦЕЛИКОМ — звездочки по краям нужно дописать самому."
    ""
    "   *   любое число любых символов, в том числе ноль"
    "   ?   ровно один любой символ      О?и находит Оси"
    "   #   ровно одна цифра             Кр4530#-# находит Кр45302-1"
    "   @   ровно одна буква             @@@ находит DIM и Оси"
    ""
    "Типичная ловушка: RAL7024 находит 2 слоя, RAL70#4 не находит ничего,"
    "а *RAL70#4* снова находит те же 2 слоя."
    "Запятая означает ИЛИ: Кр45302*,Кр45303*."
    "Тильда в начале означает КРОМЕ: ~*невидимый* скрывает невидимые блоки."
    "Смена запроса сбрасывает выделение слоев — отбор начинается заново."
    ""
    "Фильтры слоев (групповые фильтры AutoCAD)"
    "Фильтр «Мои» включает групповой фильтр «Стройплэкс» со всеми вложенными"
    "группами, в том числе групповой фильтр «Отключенные»."
    "Фасады включает фильтры с именем на «Фасад» (Фасад - Облицовка и другие)."
    "Витражи включает фильтры с именем на «Витраж» или «Фонар»."
    "Окна включает фильтры с именем на «Окн» (Окна, Окна ПВХ)."
    "Имена сравниваются без учета регистра и пробелов по краям."
    "Знак * означает любую последовательность: Окн* находит Окна и Окна ПВХ."
    "Несколько галочек объединяют слои, повторяющиеся слои не дублируются."
    "Слои, выбранные в списке вручную, имеют приоритет над фильтрами."
    "Если фильтр не нашел слоев, задача не запускается — проверьте имена фильтров."
    "Анонимные блоки — отдельная галочка, к фильтрам слоев не относится."
    ""
    "Вывод"
    "XLS и TXT создают внешние файлы. AutoCAD создает таблицу или карту"
    "непосредственно в текущем чертеже. Можно включить несколько вариантов."
    ""
    "Поиск"
    "Кнопка Поиск открывает окно поиска по атрибутам и видимостям."
    "Подробнее — раздел 10."
    ""
    "4. ЗАДАЧИ"
    "Фасонка"
    "Собирает фасонные элементы и группирует их по названию, размеру и длине."
    "Для расчета длины у элемента должно быть заполнено свойство ДЛИНА."
    ""
    "Подсистема"
    "Собирает элементы подсистемы. Для обозначения учитывается выбранный"
    "вид элемента, а если он не задан — его исходное название."
    ""
    "Облицовка"
    "Собирает контуры облицовки и блоки кассет или панелей."
    "Для контуров и блоков можно задать разные слои и разные маски названий."
    "Классификация ПОДРЕЗНАЯ сохраняется автоматически."
    ""
    "Витраж"
    "Пока работает как заглушка. Настройки уже сохраняются и будут"
    "использованы после появления полноценного модуля Витража."
    ""
    "Заполнение"
    "Собирает элементы заполнения и использует дополнительные подписи"
    "внутри блоков, в том числе ВИТРАЖ и МАРКА, если они заполнены."
    ""
    "Раскрой хлыста"
    "Формирует карту раскроя длинных заготовок, рамку и готовый блок карты."
    ""
    "Раскрой листа"
    "Формирует карту раскроя листового материала, рамку и готовый блок карты."
    ""
    "5. РЕЖИМЫ ОТЧЕТА"
    "Подробный — отдельные позиции с группировкой по исходным данным."
    "Краткий — сводные группы и итоговые количества."
    "Оба режима используют одинаковые настройки слоев и блоков."
    ""
    "6. ОКНО НАСТРОЕК"
    "Кнопка Настройки открывает отдельное окно и сохраняет файл"
    "AutoExtraction/settings.ini рядом с программой."
    "Настройки общие для подробного и краткого отчетов."
    ""
    "Для обычных задач задаются маски слоев и названий блоков."
    "Для Облицовки отдельно задаются слои контуров, слои блоков и названия блоков."
    "Для карт задаются входные маски, имя результата и слои карты."
    ""
    "7. МАСКИ И СПЕЦИАЛЬНЫЕ ЗНАЧЕНИЯ"
    "Маски работают по правилам поиска AutoCAD:"
    "* — любая последовательность символов;  ? — один символ."
    "Несколько масок объединяются по ИЛИ. Пример: Фасонка*;Железо*."
    "Это маски окна Настройки — здесь варианты разделяются точкой с запятой."
    "В полях Поиск главного окна действуют те же * и ?, плюс # (цифра)"
    "и @ (буква), а варианты там разделяются запятой: Кр45302*,Кр45303*."
    "CURRENT означает активный слой AutoCAD."
    "Метка {DWG} в шаблоне заменяется именем текущего файла чертежа."
    ""
    "8. КАРТЫ РАСКРОЯ"
    "Шаблон задает имя готового блока карты."
    "Если такое имя уже занято, программа добавляет суффикс 0, 1 и далее."
    "Слой блока результата и слой рамки настраиваются отдельно."
    "Внутренние элементы карты сохраняют свои рабочие слои."
    ""
    "9. ЗАЩИТНЫЕ ПРАВИЛА"
    "Слой Невидимые всегда исключается из обработки."
    "Ранее созданные карты раскроя также не попадают в новый исходный набор."
    "Эти исключения нельзя отменить маской *."
    ""
    "10. ПОИСК БЛОКОВ"
    "Кнопка Поиск в диспетчере открывает окно поиска блоков."
    "Режим выбирается радиокнопкой: Все блоки, Блоки с атрибутами или Видимости блоков."
    "Поле Блок сужает список блоков по маске; действует во всех режимах."
    "В режиме Все блоки поле Значение сравнивает только с длиной; пунктов нет."
    "Введите условия и нажмите Enter. Пустое поле не ограничивает."
    "Выбрать — выделяет найденные вставки в чертеже."
    "Выбрать подобное — выделяет во всем чертеже вставки, подобные образцу"
    "по выбранному блоку, видимости или атрибуту (и значению, если оно введено)."
    "Подсчёт — открывает окно с погонажем и площадью блоков."
    "Сбросить выбор — снимает выбор, окно остаётся открытым."
    "Закрыть или Esc — закрыть окно."
    ""
    "11. ПЛАГИНЫ"
    "Кнопка Плагины… в диспетчере открывает список плагинов."
    "Добавить… выбирает файл .lsp. Изменить путь… и Удалить — для строки."
    "ОК записывает список в settings.ini, Отмена ничего не меняет."
    "Файл с именем, которое уже есть в списке, заменяет путь этой записи."
    "Плагины грузятся при RELOAD после модулей проекта."
    "Статус НЕ НАЙДЕН — файл по пути не найден, плагин не загружается."
    "Программа не знает содержимого плагинов: проверяет скобки,"
    "кодировку и совпадение имён функций (предупреждение в логе)."
    ""
    "12. ОБНОВЛЕНИЕ ПРОГРАММЫ"
    "После обновления файлов загрузите reload.lsp и выполните RELOAD."
    "Затем снова запустите EXTRACTION."
    "Постоянные изменения выполняйте через кнопку Настройки."
  )
)

(defun ae-help-ui-open (/ root dcl-file dcl-path dcl-id)
  (setq root
    (if (= (type ae-settings-root) 'SUBR)
      (ae-settings-root)
      nil))
  ;; Try the support path first, then the project root and a relative path.
  (setq dcl-file (findfile "help.dcl"))
  (if (null dcl-file)
    (setq dcl-file (findfile "Extraction\\help.dcl")))
  (if (and (null dcl-file) root)
    (progn
      (setq dcl-path (strcat root "\\Extraction\\help.dcl"))
      (if (findfile dcl-path) (setq dcl-file dcl-path))
    )
  )
  (if (null dcl-file)
    (progn
      (alert "Не найден Extraction\\help.dcl.")
      nil)
    (progn
      (setq dcl-id (load_dialog dcl-file))
      (if (< dcl-id 0)
        (progn
          (alert "Не удалось загрузить окно справки.")
          nil)
        (if (new_dialog "extraction_help_dialog" dcl-id)
          (progn
            (start_list "help_lines")
            (foreach line *AE-HELP-LINES* (add_list line))
            (end_list)
            (action_tile "btn_help_close" "(done_dialog 0)")
            (start_dialog)
            (unload_dialog dcl-id)
            T)
          (progn
            (unload_dialog dcl-id)
            (alert "Не удалось открыть окно справки.")
            nil)))))
)

;; HELP.LSP загружен (ред. 3: поиск по атрибутам и видимостям, плагины).
(princ)
