;;; ============================================================
;;; RELOAD.LSP
;;; Автоматическая перезагрузка AutoExtraction
;;; AutoCAD 2016+
;;;
;;; Возможности:
;;;   - определяет корень проекта по extraction.lsp;
;;;   - загружает common-модули в правильном порядке;
;;;   - загружает Extraction-модули в правильном порядке;
;;;   - проверяет наличие каждого файла;
;;;   - перехватывает ошибки загрузки;
;;;   - точно сообщает имя файла, вызвавшего ошибку;
;;;   - продолжает загрузку следующих модулей;
;;;
;;; ДОБАВЛЕНО:
;;;   - автоподгрузка tests\chkparens.lsp (если файл существует);
;;;   - пост-диагностика скобок ТОЛЬКО при ошибке загрузки:
;;;     печатает номер строки с небалансом упавшего файла.
;;;     Guard: (= (type chk-parens-scan) 'SUBR) - если проверка
;;;     не загружена, RELOAD работает как раньше.
;;;   - при сбое загрузки - тихий CHKALL по всем файлам (см. ниже).
;;;     Флаг: *ae-reload-chkall-on-error* nil - выключить.
;;; ============================================================

(vl-load-com)

;; ------------------------------------------------------------
;; Автопроверка скобок после сбоя загрузки.
;;
;; Раньше CHKALL гонялся на КАЖДЫЙ RELOAD - его зовёт MARKZ
;; (ред. 48.36+, TEST 00 -> c:CHKALL). В AutoExtraction проверка
;; нужна только когда что-то не загрузилось: она показывает все
;; проблемные файлы, а не только первый упавший. Печатает только
;; проблемные файлы (тихий режим chkparens.lsp).
;; ------------------------------------------------------------
(if (not (boundp '*ae-reload-chkall-on-error*))
  (setq *ae-reload-chkall-on-error* T))

;; ------------------------------------------------------------
;; Списки модулей - на верхнем уровне файла.
;; c:RELOAD при каждом запуске перечитывает СЕБЯ с диска (см. ниже),
;; поэтому эти списки всегда актуальны - даже если команда RELOAD
;; в памяти AutoCAD определена старой редакцией.
;; ------------------------------------------------------------
(setq *ae-reload-common-files*
  '(
    "task-utils.lsp"
    "settings-utils.lsp"
    "perf-utils.lsp"
    "layer-utils.lsp"
    "select-utils.lsp"
    "excel-utils.lsp"
    "table-utils.lsp"
    "txt-utils.lsp"
    "validation-utils.lsp"
  )
)

(setq *ae-reload-extraction-files*
  '(
    "fasonka.lsp"
    "subsystem.lsp"
    "cladding.lsp"
    "zapolnenie.lsp"
    "settings.lsp"
    "help.lsp"
    "extraction.lsp"
    "cutline.lsp"
    "cutsheet.lsp"
    "blockrename.lsp"
    "searchattvis.lsp"
  )
)

;; ------------------------------------------------------------
;; ПЛАГИНЫ: сторонние модули. Программа не знает их содержимого.
;; Реестр - секция [plugins] в settings.ini, его пишет окно
;; «Настройки» (кнопка «Плагины...»). Одна запись на плагин:
;;   plugin.N.name - имя файла, plugin.N.path - полный путь (может быть пуст).
;; Путь задан - грузим по нему; файла нет - строка НЕ НАЙДЕН в логе
;; (без отката на другой путь). Путь пуст - Plugins\\<имя> в проекте.
;; Порядок загрузки - порядок записей реестра.
;; ------------------------------------------------------------

(defun ae-reload-kv (items key)
  (cdr (assoc key items))
)

(defun ae-reload-plugin-registry (/ root path f line section parsed items out i name ppath)
  (setq root (ae-reload-root))
  (setq path (if root (strcat root "\\settings.ini") nil))
  (setq items '())
  (setq section "")
  (if (and path (setq f (open path "r")))
    (progn
      (while (setq line (read-line f))
        (setq parsed (ae-settings-read-line line section))
        (setq section (car parsed))
        (if (and (= section "plugins") (cadr parsed))
          (setq items (cons (cons (cadr parsed) (caddr parsed)) items))
        )
      )
      (close f)
    )
  )
  (setq items (reverse items))
  ;; Без счётчика: идём по plugin.1, plugin.2, ... пока есть plugin.N.name.
  (setq i 1)
  (setq out '())
  (while (and (<= i 99) (ae-reload-kv items (strcat "plugin." (itoa i) ".name")))
    ;; Значения уже обрезаны ae-settings-read-line. Не использовать (or ...):
    ;; в AutoLISP он возвращает T, а не значение.
    (setq name (if (ae-reload-kv items (strcat "plugin." (itoa i) ".name"))
                 (ae-reload-kv items (strcat "plugin." (itoa i) ".name")) ""))
    (setq ppath (if (ae-reload-kv items (strcat "plugin." (itoa i) ".path"))
                  (ae-reload-kv items (strcat "plugin." (itoa i) ".path")) ""))
    (if (> (strlen name) 0)
      (setq out (cons (list name ppath) out))
    )
    (setq i (1+ i))
  )
  (reverse out)
)

(defun ae-reload-plugin-resolve (name ppath / root)
  ;; Полный путь к файлу плагина или nil.
  ;; Путь из реестра задан - только он: нет файла - nil (НЕ НАЙДЕН).
  ;; Путь пуст - Plugins\<имя> внутри проекта.
  (setq root (ae-reload-root))
  (cond
    ((> (strlen ppath) 0) (findfile ppath))
    ((and root (findfile (strcat root "\\Plugins\\" name))))
    (T nil)
  )
)

(defun ae-reload-token-end (s / i n)
  (setq i 1)
  (setq n (strlen s))
  (while (and (<= i n) (not (member (substr s i 1) '(" " ")"))))
    (setq i (1+ i))
  )
  (substr s 1 (1- i))
)

(defun ae-reload-plugin-defuns (path / f line lines depths depth name out)
  ;; Имена (defun ...) верхнего уровня из файла плагина; сам файл не
  ;; интерпретируется. Вложенные defun (локальные обработчики *error*
  ;; внутри команд) объявлениями плагина не считаются: для каждой строки
  ;; проверяется глубина скобок, накопленная к её началу.
  (setq out '() lines '())
  (if (setq f (open path "r"))
    (progn
      (while (setq line (read-line f))
        (setq lines (cons line lines))
      )
      (close f)
    )
  )
  (setq lines (reverse lines))
  (setq depths (ae-reload-line-balances lines))
  (setq depth 0)
  (foreach line lines
    (setq line (ae-settings-trim line))
    (if (and (= depth 0)
             (> (strlen line) 7)
             (= (strcase (substr line 1 7)) "(DEFUN "))
      (progn
        (setq name (ae-reload-token-end (substr line 8)))
        (if (> (strlen name) 0)
          (setq out (cons name out))
        )
      )
    )
    (setq depth (car depths))
    (setq depths (cdr depths))
  )
  out
)

(defun ae-reload-plugin-conflicts (path names taken / nm)
  ;; Имена функций плагина, уже занятые проектом (по файлам этого прогона)
  ;; или предыдущим плагином, - предупреждение в логе. Загрузка продолжается.
  ;; Возвращает taken, пополненный именами этого плагина.
  (foreach nm names
    (if (member (strcase nm) taken)
      (princ (strcat "\n[RELOAD][PLUGINS] ВНИМАНИЕ: функция " nm
                     " уже определена (проект или другой плагин); плагин "
                     path " её перезапишет"))
    )
  )
  (append (mapcar 'strcase names) taken)
)

;; ------------------------------------------------------------
;; Автоподгрузка проверки скобок (дешево: только defun'ы,
;; без сканирования). Если файла нет - молча пропускаем.
;; Загрузка обёрнута в перехват: сбой в tests\chkparens.lsp не должен
;; обрывать загрузку САМОГО reload.lsp (иначе молча теряются его
;; функции, в том числе ae-reload-load-file и c:RELOAD).
;; ------------------------------------------------------------
(setq *ae-chk-ok* nil)
(if (findfile "extraction.lsp")
  (progn
    (setq ae-chk-path
      (strcat
        (vl-filename-directory
          (vl-filename-directory (findfile "extraction.lsp")))
        "\\tests\\chkparens.lsp"))
    (if (findfile ae-chk-path)
      (progn
        (setq ae-chk-res (vl-catch-all-apply 'load (list ae-chk-path)))
        (if (vl-catch-all-error-p ae-chk-res)
          (princ (strcat "\n[RELOAD] ВНИМАНИЕ: не загружен " ae-chk-path ": "
                         (vl-catch-all-error-message ae-chk-res)
                         " - поиск формы со сбоем будет встроенным"))
          (setq *ae-chk-ok* T)
        )
      )
    )
  )
)


(defun ae-reload-rev-count (paths / f cnt found line ff)
  ;; U3: сколько модулей объявили маркер редакции "(ред. N" в своём файле.
  ;; Чтение фаилов сырое (байтовое) - ищем подстроку как есть.
  (setq cnt 0)
  (foreach f paths
    (setq found nil ff (open f "r"))
    (if ff
      (progn
        (while (and (not found) (setq line (read-line ff)))
          ;; признак: "(ред. N" (стандарт) или ", ред. N" (стиль CLADDING)
          (if (or (vl-string-search "(ред. " line)
                  (vl-string-search ", ред. " line))
            (setq found T)))
        (close ff)))
    (if found (setq cnt (1+ cnt))))
  cnt)


;; ============================================================
;; ВСТРОЕННЫЙ ПОИСК ФОРМЫ СО СБОЕМ ЗАГРУЗКИ (резерв CHKLOAD)
;; Нужен, когда tests\chkparens.lsp недоступен, не загрузился или он
;; старой версии: файл режется на префиксы по границам верхнеуровневых
;; форм (строка начинается с "(" при нулевом балансе), каждый префикс
;; пишется во временный файл и загружается; первый падающий префикс
;; указывает форму со сбоем. Метки те же, что у команды CHKLOAD.
;; ============================================================

;; Тип символа, даже если символ не определён (nil вместо ошибки)
(defun ae-reload-sym-type (sym / r)
  (setq r (vl-catch-all-apply 'type (list (vl-catch-all-apply 'eval (list sym)))))
  (if (vl-catch-all-error-p r) nil r)
)

;; Баланс скобок после каждой строки (строки в кавычках и комментарии
;; не считаются)
(defun ae-reload-line-balances (lines / out bal line i ch instr incomm skip)
  (setq out '() bal 0)
  (foreach line lines
    (setq i 1 instr nil incomm nil skip nil)
    (while (<= i (strlen line))
      (setq ch (substr line i 1))
      (cond
        (skip (setq skip nil))
        (incomm nil)
        ((and instr (= ch "\\")) (setq skip T))
        (instr (if (= ch "\"") (setq instr nil)))
        ((= ch ";") (setq incomm T))
        ((= ch "\"") (setq instr T))
        ((= ch "(") (setq bal (1+ bal)))
        ((= ch ")") (setq bal (1- bal)))
      )
      (setq i (1+ i))
    )
    (setq out (cons bal out))
  )
  (reverse out)
)

;; Записать первые k-1 строк (перевод LF) во временный файл и загрузить.
;; nil = префикс загрузился; иначе - текст ошибки загрузки.
(defun ae-reload-probe-try (lines k tmp / i f res line)
  (setq i 0)
  (setq f (open tmp "w"))
  (if (null f)
    "не открыт временный файл"
    (progn
      (while (< i (1- k))
        (setq line (nth i lines))
        (if (and (> (strlen line) 0) (= (substr line (strlen line)) "\r"))
          (setq line (substr line 1 (1- (strlen line))))
        )
        (write-line line f)
        (setq i (1+ i))
      )
      (close f)
      (setq res (vl-catch-all-apply 'load (list tmp)))
      (vl-file-delete tmp)
      (if (vl-catch-all-error-p res)
        (vl-catch-all-error-message res)
        nil)
    )
  )
)

;; Напечатать, в какой форме сбой загрузки файла
(defun ae-reload-probe-file (path / f line lines tot bals bounds i lo hi mid tmp
                             found n prev cur msg bad)
  (setq f (open path "r"))
  (if (null f)
    (princ (strcat "\n[CHKLOAD] не открыт: " path))
    (progn
      (setq lines '())
      (while (setq line (read-line f)) (setq lines (cons line lines)))
      (close f)
      (setq lines (reverse lines) n (length lines) tot 0)
      (foreach line lines (setq tot (+ tot (strlen line))))
      (setq bals (ae-reload-line-balances lines))
      (setq bounds '() prev 0 i 0)
      (foreach line lines
        (if (and (= (substr line 1 1) "(") (= prev 0))
          (setq bounds (cons (1+ i) bounds)))
        (setq prev (nth i bals))
        (setq i (1+ i))
      )
      (setq bounds (reverse bounds))
      (if (null bounds)
        (princ (strcat "\n[CHKLOAD] " path ": границы форм не найдены"))
        (progn
          (setq tmp (vl-catch-all-apply 'vl-filename-mktemp
                                        (list "ae-probe" (vl-filename-directory path) ".lsp")))
          (if (or (vl-catch-all-error-p tmp) (null tmp))
            (setq tmp (strcat (vl-filename-directory path) "\\ae-probe-tmp.lsp")))
          (princ (strcat "\n[CHKLOAD] " path ", строк " (itoa n)
                         ", символов " (itoa tot)
                         ", форм верхнего уровня " (itoa (length bounds))))
          (setq msg (ae-reload-probe-try lines (1+ n) tmp))
          (if (null msg)
            (princ "\n[CHKLOAD] копия файла (LF) грузится, а сам файл — нет (дело не в содержимом форм)")
            (progn
              (princ (strcat "\n[CHKLOAD] загрузка всего файла: " msg))
              (setq lo 0 hi (1- (length bounds)) found nil)
              (while (<= lo hi)
                (setq mid (fix (/ (+ lo hi) 2.0)))
                (if (ae-reload-probe-try lines (nth mid bounds) tmp)
                  (progn (setq found mid hi (1- mid)))
                  (setq lo (1+ mid))
                )
              )
              ;; Префикс перед формой k падает, префикс перед формой k-1
              ;; грузится -> дефект в форме k-1. Падает только целый файл -
              ;; дефект в последней форме.
              (setq bad (if found (if (> found 0) (1- found) 0) (1- (length bounds))))
              (setq cur (nth bad bounds))
              (setq msg (ae-reload-probe-try lines
                          (if found (nth found bounds) (1+ n)) tmp))
              (princ (strcat "\n[CHKLOAD] СБОЙ В ФОРМЕ №" (itoa (1+ bad)) ", строки "
                             (itoa cur) ".."
                             (itoa (if (< (1+ bad) (length bounds))
                                     (1- (nth (1+ bad) bounds))
                                     n))
                             " | ошибка: " (if msg msg "нет")))
              (setq i 0)
              (foreach line lines
                (setq i (1+ i))
                (if (and (>= i cur) (<= i (+ cur 11)))
                  (princ (strcat "\n[CHKLOAD]   " (itoa i) ": " (substr line 1 160)))
                )
              )
            )
          )
        )
      )
    )
  )
  (princ)
)

;; Запуск поиска: chk-load-find из tests\chkparens.lsp, а если его нет -
;; встроенный поиск. Ошибки самого поиска наружу не выходят.
(defun ae-reload-chkload-run (path / res)
  (if (member (ae-reload-sym-type 'chk-load-find) '(SUBR USUBR))
    (progn
      (setq res (vl-catch-all-apply 'chk-load-find (list path)))
      (if (vl-catch-all-error-p res)
        (princ (strcat "\n[CHKLOAD] поиск прерван: " (vl-catch-all-error-message res)))
      )
    )
    (ae-reload-probe-file path)
  )
  (princ)
)

(defun ae-reload-load-file
       (fullpath note / result)

  ;; ------------------------------------------------------------
  ;; Загрузка одного LSP-файла с перехватом ошибки
  ;; ------------------------------------------------------------

  (if (not (findfile fullpath))
    (progn
      (princ
        (strcat
          "\nНЕ НАЙДЕН: "
          fullpath
        )
      )
      nil
    )
    (progn

      (setq result
        (vl-catch-all-apply
          'load
          (list fullpath)
        )
      )

      (if (vl-catch-all-error-p result)
        (progn
          (princ
            (strcat
              "\nОШИБКА ЗАГРУЗКИ: "
              fullpath
              "\n  Причина: "
              (vl-catch-all-error-message result)
              (if (vl-file-size fullpath)
                (strcat "\n  Размер файла: " (itoa (vl-file-size fullpath)) " байт")
                "")
            )
          )
          ;; ----------------------------------------------------
          ;; Пост-диагностика: показываем строку с небалансом
          ;; скобок упавшего файла (только при ошибке загрузки)
          ;; ----------------------------------------------------
          (if (= (type chk-parens-scan) 'SUBR)
            (progn
              (princ "\n--- диагностика файла: скобки, строки, скрытые байты ---")
              (chk-parens-scan fullpath nil)
            )
          )
          ;; Локализация сбоя: бисекция по верхнеуровневым формам (CHKLOAD).
          ;; Основной инструмент - chk-load-find из tests\chkparens.lsp;
          ;; если он недоступен (нет файла, файл не загрузился или он
          ;; старой версии), работает встроенный поиск в самом reload.lsp.
          (princ "\n--- поиск формы со сбоем (CHKLOAD) ---")
          (ae-reload-chkload-run fullpath)
          nil
        )
        (progn
          (if (not (and (boundp '*ae-reload-quiet*) *ae-reload-quiet*))
            (princ
              (strcat
                "\nЗагружен: "
                fullpath
                (if note
                  (strcat "  [" note "]")
                  ""
                )
              )
          )
          )
          T
        )
      )
    )
  )
)


;; ------------------------------------------------------------
;; Таблица команд при загрузке. Модуль регистрирует свои строки
;; (ae-banner-add) в конце файла; RELOAD печатает таблицу после модулей.
;; ------------------------------------------------------------
(if (not (boundp '*ae-banner-items*))
  (setq *ae-banner-items* '()))

(defun ae-banner-add (module rows / keep it)
  (setq keep '())
  (foreach it *ae-banner-items*
    (if (/= (car it) module)
      (setq keep (cons it keep))))
  (setq *ae-banner-items* (reverse (cons (cons module rows) keep)))
)

(defun ae-banner-rep (ch n / s)
  (setq s "")
  (repeat n (setq s (strcat s ch)))
  s
)

(defun ae-banner-pad (s n)
  (strcat s (ae-banner-rep " " (- n (strlen s))))
)

(defun ae-banner-rev (r / v)
  (setq v (if (and (listp r) (caddr r)) (caddr r) ""))
  (if (= (type v) 'STR) v "")
)

(defun ae-banner-print ( / rows w1 w2 w3 sep r it)
  (setq rows '())
  (foreach it *ae-banner-items*
    (foreach r (cdr it)
      (setq rows (cons r rows))))
  (setq rows (reverse rows))
  (if rows
    (progn
      (setq w1 (max 7 (apply 'max (mapcar '(lambda (x) (strlen (car x))) rows))))
      (setq w2 (max 10 (apply 'max (mapcar '(lambda (x) (strlen (cadr x))) rows))))
      (setq w3 (max 4 (apply 'max (mapcar '(lambda (x) (strlen (ae-banner-rev x))) rows))))
      (setq sep (strcat "  +" (ae-banner-rep "-" (+ w1 2)) "+"
                        (ae-banner-rep "-" (+ w2 2)) "+"
                        (ae-banner-rep "-" (+ w3 2)) "+"))
      (princ (strcat "\n" sep))
      (princ (strcat "\n  | " (ae-banner-pad "КОМАНДА" w1)
                     " | " (ae-banner-pad "ЧТО ДЕЛАЕТ" w2)
                     " | " (ae-banner-pad "РЕД." w3) " |"))
      (princ (strcat "\n" sep))
      (foreach r rows
        (princ (strcat "\n  | " (ae-banner-pad (car r) w1)
                       " | " (ae-banner-pad (cadr r) w2)
                       " | " (ae-banner-pad (ae-banner-rev r) w3) " |")))
      (princ (strcat "\n" sep))
    )
  )
  (princ)
)

(defun c:RELOAD
       ( / root
           common
           extraction-dir
           f
           fullpath
           common-files
           extraction-files
           plugin-items
           plugin-seen
           plugin-rec
           plugin-name
           plugin-path
           plugin-res
           plugin-names
           plugin-missing
           plugin-resolved
           plugin-taken
           it
           ok
           errors
           missing
           ok-plugins
           revcnt
           revpaths)
  (setq *ae-banner-items* '())

  ;; ------------------------------------------------------------
  ;; Заголовок
  ;; ------------------------------------------------------------

  (princ
    "\n============================================="
  )
  (princ
    "\n AutoExtraction RELOAD"
  )
  (princ
    "\n============================================="
  )


  ;; ------------------------------------------------------------
  ;; Определяем корень проекта
  ;; ------------------------------------------------------------

  (setq root
    (if (findfile "extraction.lsp")
      (vl-filename-directory
        (vl-filename-directory
          (findfile "extraction.lsp")
        )
      )
      nil
    )
  )


  ;; ------------------------------------------------------------
  ;; Если extraction.lsp не найден
  ;; ------------------------------------------------------------

  (if (not root)
    (progn
      (princ
        "\nОШИБКА: не найден extraction.lsp."
      )
      (princ
        "\nRELOAD прерван."
      )
      (princ)
    )

    (progn

      ;; --------------------------------------------------------
      ;; Пути
      ;; --------------------------------------------------------

      (setq common
        (strcat root "\\common\\")
      )

      (setq extraction-dir
        (strcat root "\\Extraction\\")
      )


      (princ
        (strcat
          "\nКорень проекта: "
          root
        )
      )

      (princ
        (strcat
          "\nCommon: "
          common
        )
      )

      (princ
        (strcat
          "\nExtraction: "
          extraction-dir
        )
      )


      ;; --------------------------------------------------------
      ;; Счетчики
      ;; --------------------------------------------------------

      (setq ok 0)
      (setq errors 0)
      (setq missing 0)
      (setq ok-plugins 0)


      ;; --------------------------------------------------------
      ;; COMMON
      ;; --------------------------------------------------------

      ;; Самообновление: перечитать себя с диска - иначе добавленные
      ;; модули не загружаются до перезапуска AutoCAD
      ;; (регрессия 2026-09-22: no function definition TU-PARSE-INT-LIST).
      (setq *ae-reload-self* (vl-catch-all-apply 'load (list (strcat root "\\reload.lsp"))))
      ;; Сверку версий печатает верхний уровень перечитанного reload.lsp.
      ;; Здесь — только если перечитать не удалось: иначе о составе
      ;; комплекта не сообщит никто (в сессии остаются старые определения).
      (if (vl-catch-all-error-p *ae-reload-self*)
        (progn
          (princ (strcat "\n[RELOAD] ВНИМАНИЕ: reload.lsp не перечитан с диска: "
                         (vl-catch-all-error-message *ae-reload-self*)
                         " - в сессии работают определения из памяти AutoCAD"))
          (princ (strcat "\n" (ae-reload-version-line)))
        )
      )

      (setq common-files *ae-reload-common-files*)


      (princ
        "\n"
      )
      (setq *ae-reload-quiet* T)


      (foreach f common-files

        (setq fullpath
          (strcat common f)
        )

        (if (ae-reload-load-file fullpath nil)
          (setq ok (1+ ok))
          (if (findfile fullpath)
            (setq errors (1+ errors))
            (setq missing (1+ missing))
          )
        )
      )


      ;; --------------------------------------------------------
      ;; EXTRACTION
      ;; --------------------------------------------------------

      (setq extraction-files *ae-reload-extraction-files*)


      (princ
        "\n"
      )


      (foreach f extraction-files

        (setq fullpath
          (strcat extraction-dir f)
        )

        (if (ae-reload-load-file fullpath nil)
          (setq ok (1+ ok))
          (if (findfile fullpath)
            (setq errors (1+ errors))
            (setq missing (1+ missing))
          )
        )
      )


      ;; Модули проекта загружены тихо; печатаем таблицу команд.
      (setq *ae-reload-quiet* nil)
      (ae-banner-add "RELOAD" (list
        (list "RELOAD" "перезагрузка модулей и плагинов")
        (list "CHKALL" "проверка скобок всех модулей и плагинов")
        (list "CHKALLFULL" "то же с полным отчётом по каждому файлу")
        (list "CHKFILE" "проверка одного файла")
        (list "CHKLOAD" "поиск формы со сбоем загрузки")))
      (ae-banner-print)

      ;; --------------------------------------------------------
      ;; PLUGINS (сторонние модули)
      ;; --------------------------------------------------------
      ;; Реестр - секция [plugins] settings.ini. Пустой реестр - молча.
      ;; Повтор имени - пропуск с записью. Путь задан, файла нет - НЕ НАЙДЕН.
      ;; Имена функций проекта: сканируем файлы, которые RELOAD только что
      ;; загрузил. Плагин, объявивший такое же имя, его перекроет.
      (setq plugin-taken '())
      (foreach f common-files
        (setq plugin-taken
          (append (mapcar 'strcase (ae-reload-plugin-defuns (strcat common f)))
                  plugin-taken)))
      (foreach f extraction-files
        (setq plugin-taken
          (append (mapcar 'strcase (ae-reload-plugin-defuns (strcat extraction-dir f)))
                  plugin-taken)))
      (setq plugin-taken
        (append (mapcar 'strcase (ae-reload-plugin-defuns (strcat root "\\reload.lsp")))
                plugin-taken))

      (setq plugin-items '())
      (setq plugin-seen '())
      (setq plugin-missing 0)
      (setq plugin-resolved '())
      (foreach plugin-rec (ae-reload-plugin-registry)
        (setq plugin-name (car plugin-rec))
        (setq plugin-path (cadr plugin-rec))
        (cond
          ((member (strcase plugin-name) plugin-seen)
           (princ (strcat "\n[RELOAD][PLUGINS] повтор имени " plugin-name " - пропущен")))
          (T
           (setq plugin-seen (cons (strcase plugin-name) plugin-seen))
           (if (and (> (strlen plugin-path) 0)
                    (/= (strcase (vl-filename-base plugin-name))
                        (strcase (vl-filename-base plugin-path))))
             (princ (strcat "\n[RELOAD][PLUGINS] ВНИМАНИЕ: имя " plugin-name
                            " не совпадает с файлом пути " plugin-path))
           )
           (setq plugin-items (cons (list plugin-name plugin-path) plugin-items)))
        )
      )
      (setq plugin-items (reverse plugin-items))

      (if (> (length plugin-items) 0)
        (progn
          (princ "\n")
          (princ "\n--- PLUGINS ---")

          (foreach plugin-rec plugin-items
            (setq plugin-res (ae-reload-plugin-resolve (car plugin-rec) (cadr plugin-rec)))
            (if (null plugin-res)
              (progn
                (princ (strcat "\n[RELOAD][PLUGINS] НЕ НАЙДЕН по пути "
                               (if (> (strlen (cadr plugin-rec)) 0)
                                 (cadr plugin-rec)
                                 (strcat "Plugins\\" (car plugin-rec)))
                               " - плагин " (car plugin-rec) " не загружен"))
                (setq plugin-missing (1+ plugin-missing))
              )
              (progn
                (setq plugin-resolved (cons plugin-res plugin-resolved))
                (setq plugin-names (ae-reload-plugin-defuns plugin-res))
                (setq plugin-taken (ae-reload-plugin-conflicts plugin-res plugin-names plugin-taken))
                (if (ae-reload-load-file plugin-res nil)
                  (progn
                    (setq ok-plugins (1+ ok-plugins)))
                  (setq errors (1+ errors))
                )
              )
            )
          )
        )
      )

      ;; --------------------------------------------------------
      ;; Итог
      ;; --------------------------------------------------------

      ;; U3: номер прогона RELOAD за сессию (выживает перечитывание reload.lsp,
      ;; т.к. сброса на ноль нет) и счётчик маркеров редакции.
      (if (null (boundp '*ae-reload-run*))
        (setq *ae-reload-run* 0))
      (setq *ae-reload-run* (1+ *ae-reload-run*))
      (setq revpaths '())
      (foreach f common-files
        (setq revpaths (cons (strcat common f) revpaths)))
      (foreach f extraction-files
        (setq revpaths (cons (strcat extraction-dir f) revpaths)))
      (foreach it plugin-resolved
        (setq revpaths (cons it revpaths)))
      (setq revcnt (ae-reload-rev-count revpaths))

      (princ
        "\n"
      )
      (princ
        "\n============================================="
      )

      (princ
        (strcat
          "\n RELOAD завершен (прогон #"
          (itoa *ae-reload-run*)
          ")."
        )
      )
      (princ
        (strcat
          "\n Маркер редакции: "
          (itoa revcnt)
          " из "
          (itoa (+ (length common-files) (length extraction-files) (length plugin-items)))
          " модулей."
        )
      )

      (princ
        (strcat
          "\n Успешно загружено модулей: "
          (itoa ok)
        )
      )
      (princ
        (strcat
          "\n Успешно загружено плагинов: "
          (itoa ok-plugins)
        )
      )

      (princ
        (strcat
          "\n Ошибок загрузки: "
          (itoa errors)
        )
      )

      (princ
        (strcat
          "\n Не найдено файлов: "
          (itoa missing)
        )
      )

      (princ
        "\n============================================="
      )


      ;; --------------------------------------------------------
      ;; Дополнительное предупреждение
      ;; --------------------------------------------------------

      (if (> errors 0)
        (princ
          "\nВНИМАНИЕ: имеются ошибки загрузки. См. строки выше."
        )
      )

      ;; Доктор только при сбое: один проход CHKALL в тихом режиме.
      ;; Он найдёт и другие битые файлы, а не только первый упавший.
      (if (and (> errors 0)
               (not (and (boundp '*ae-reload-chkall-on-error*)
                         (null *ae-reload-chkall-on-error*)))
               (member (type chk-all-run) '(SUBR USUBR)))
        (progn
          (princ "\n--- CHKALL: проверка всех файлов после сбоя загрузки ---")
          (vl-catch-all-apply 'chk-all-run (list T))))

      (if (> plugin-missing 0)
        (princ
          "\nВНИМАНИЕ: плагины не найдены по пути из реестра (см. строки выше)."
        )
      )

      (if (> missing 0)
        (princ
          "\nВНИМАНИЕ: некоторые файлы проекта не найдены."
        )
      )
    )
  )

  (princ)
)



;; ------------------------------------------------------------
;; Сверка версий комплекта. Печатается на ВЕРХНЕМ уровне, то есть при
;; каждом чтении reload.lsp с диска (ручная загрузка и самообновление
;; внутри RELOAD). Прежде строку печатало только тело c:RELOAD, а оно
;; выполняется в редакции, загруженной ДО самообновления: если в сессии
;; осталось старое c:RELOAD, строка молча пропадала (прогон #21).
;; ------------------------------------------------------------
(defun ae-reload-root ( / p)
  (setq p (findfile "extraction.lsp"))
  (if p (vl-filename-directory (vl-filename-directory p)))
)

(defun ae-reload-size-str (path / n)
  (setq n (if path (vl-file-size path)))
  (itoa (if n n 0))
)

(defun ae-reload-version-line ( / root)
  (setq root (ae-reload-root))
  (strcat "[RELOAD] сверка версий: reload.lsp "
          (ae-reload-size-str (if root (strcat root "\\reload.lsp")))
          " байт | tests\\chkparens.lsp "
          (ae-reload-size-str (if root (strcat root "\\tests\\chkparens.lsp")))
          " байт | загружен: " (if *ae-chk-ok* "да" "нет")
          " | chk-load-find: "
          (if (member (ae-reload-sym-type 'chk-load-find) '(SUBR USUBR))
            "есть" "нет"))
)

(princ
  "\nRELOAD.LSP загружен. Команда: RELOAD"
)

(princ (strcat "\n" (ae-reload-version-line)))

(princ)
